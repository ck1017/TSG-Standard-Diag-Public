-- Modem Diagnostic Monitoring Interface API
-- Draft v2.8.2
-- 10.06.2016

--  LastUpdated
--      201610060000Z
--  OrgName
--      Verizon Wireless
--  Descr
--      MIB module for generic diagnostic applications

MDMI DEFINITIONS ::= BEGIN

IMPORTS
    OBJECT-TYPE
        FROM RFC-1212;

mdmiDebug           OBJECT IDENTIFIER ::= { mdmi(1) 1 }
mdmiLte             OBJECT IDENTIFIER ::= { mdmi(1) 2 }
mdmiGsm             OBJECT IDENTIFIER ::= { mdmi(1) 3 }
mdmiUmts            OBJECT IDENTIFIER ::= { mdmi(1) 4 }
mdmiWifi            OBJECT IDENTIFIER ::= { mdmi(1) 5 }
mdmiIms             OBJECT IDENTIFIER ::= { mdmi(1) 6 }
mdmiCommands        OBJECT IDENTIFIER ::= { mdmi(1) 7 }
mdmiLteMiddleware   OBJECT IDENTIFIER ::= { mdmi(1) 8 }
mdmiWcdma           OBJECT IDENTIFIER ::= { mdmi(1) 9 }
mdmiHsupa           OBJECT IDENTIFIER ::= { mdmi(1) 10 }
mdmiHsdpa           OBJECT IDENTIFIER ::= { mdmi(1) 11 }

-------------------------------------------------------------------------------
------      mdmiDebug                                              ------------
-------------------------------------------------------------------------------
debugConfig         OBJECT IDENTIFIER ::= { mdmiDebug 1 }
debugKpis           OBJECT IDENTIFIER ::= { mdmiDebug 2 }
debugEvents         OBJECT IDENTIFIER ::= { mdmiDebug 3 }
debugReserved       OBJECT IDENTIFIER ::= { mdmiDebug 4 }

-------------------------------------------------------------------------------
------      mdmiLte                                                ------------
-------------------------------------------------------------------------------
lteDebug    OBJECT IDENTIFIER ::= { mdmiLte 1 }
lteRrc      OBJECT IDENTIFIER ::= { mdmiLte 2 }
lteNas      OBJECT IDENTIFIER ::= { mdmiLte 3 }
lteMac      OBJECT IDENTIFIER ::= { mdmiLte 4 }
lteRlc      OBJECT IDENTIFIER ::= { mdmiLte 5 }
ltePdcp     OBJECT IDENTIFIER ::= { mdmiLte 6 }
ltePhy      OBJECT IDENTIFIER ::= { mdmiLte 7 }
lteIp       OBJECT IDENTIFIER ::= { mdmiLte 8 }
lteSupl     OBJECT IDENTIFIER ::= { mdmiLte 9 }
lteLpp      OBJECT IDENTIFIER ::= { mdmiLte 10 }
lteE911     OBJECT IDENTIFIER ::= { mdmiLte 11 }

lteRrcDebug         OBJECT IDENTIFIER ::= { lteRrc 1 }
lteRrcKpis          OBJECT IDENTIFIER ::= { lteRrc 2 }
lteRrcEvents        OBJECT IDENTIFIER ::= { lteRrc 3 }
lteRrcMessages      OBJECT IDENTIFIER ::= { lteRrc 4 }

lteNasDebug         OBJECT IDENTIFIER ::= { lteNas 1 }
lteNasKpis          OBJECT IDENTIFIER ::= { lteNas 2 }
lteNasEvents        OBJECT IDENTIFIER ::= { lteNas 3 }
lteNasMessages      OBJECT IDENTIFIER ::= { lteNas 4 }

lteMacDebug         OBJECT IDENTIFIER ::= { lteMac 1 }
lteMacKpis          OBJECT IDENTIFIER ::= { lteMac 2 }
lteMacEvents        OBJECT IDENTIFIER ::= { lteMac 3 }
lteMacMessages      OBJECT IDENTIFIER ::= { lteMac 4 }

lteRlcDebug         OBJECT IDENTIFIER ::= { lteRlc 1 }
lteRlcKpis          OBJECT IDENTIFIER ::= { lteRlc 2 }
lteRlcEvents        OBJECT IDENTIFIER ::= { lteRlc 3 }
lteRlcMessages      OBJECT IDENTIFIER ::= { lteRlc 4 }

ltePdcpDebug         OBJECT IDENTIFIER ::= { ltePdcp 1 }
ltePdcpKpis          OBJECT IDENTIFIER ::= { ltePdcp 2 }
ltePdcpEvents        OBJECT IDENTIFIER ::= { ltePdcp 3 }
ltePdcpMessages      OBJECT IDENTIFIER ::= { ltePdcp 4 }

ltePhyDebug             OBJECT IDENTIFIER ::= { ltePhy 1 }
ltePhyMeasurements      OBJECT IDENTIFIER ::= { ltePhy 2 }
ltePhyEvents            OBJECT IDENTIFIER ::= { ltePhy 3 }
ltePhyPmch              OBJECT IDENTIFIER ::= { ltePhy 4 }
ltePhyPbch              OBJECT IDENTIFIER ::= { ltePhy 5 }
ltePhyPdsch             OBJECT IDENTIFIER ::= { ltePhy 6 }
ltePhyPcfich            OBJECT IDENTIFIER ::= { ltePhy 7 }
ltePhyPdcch             OBJECT IDENTIFIER ::= { ltePhy 8 }
ltePhyPhich             OBJECT IDENTIFIER ::= { ltePhy 9 }
ltePhyPucch             OBJECT IDENTIFIER ::= { ltePhy 10 }
ltePhyPusch             OBJECT IDENTIFIER ::= { ltePhy 11 }
ltePhyPrach             OBJECT IDENTIFIER ::= { ltePhy 12 }
ltePhyEpdcch            OBJECT IDENTIFIER ::= { ltePhy 13 }

lteIpDebug         OBJECT IDENTIFIER ::= { lteIp 1 }
lteIpKpis          OBJECT IDENTIFIER ::= { lteIp 2 }
lteIpEvents        OBJECT IDENTIFIER ::= { lteIp 3 }
lteIpMessages      OBJECT IDENTIFIER ::= { lteIp 4 }

lteSuplDebug       OBJECT IDENTIFIER ::= { lteSupl 1 }
lteSuplKpis        OBJECT IDENTIFIER ::= { lteSupl 2 }
lteSuplEvents      OBJECT IDENTIFIER ::= { lteSupl 3 }
lteSuplMessages    OBJECT IDENTIFIER ::= { lteSupl 4 }

lteLppDebug         OBJECT IDENTIFIER ::= { lteLpp 1 }
lteLppKpis          OBJECT IDENTIFIER ::= { lteLpp 2 }
lteLppEvents        OBJECT IDENTIFIER ::= { lteLpp 3 }
lteLppMessages      OBJECT IDENTIFIER ::= { lteLpp 4 }

lteE911Debug         OBJECT IDENTIFIER ::= { lteE911 1 }
lteE911Kpis          OBJECT IDENTIFIER ::= { lteE911 2 }
lteE911Events        OBJECT IDENTIFIER ::= { lteE911 3 }
lteE911Messages      OBJECT IDENTIFIER ::= { lteE911 4 }

    -------------------------------------------------------------------------------
    ------      Common Fields                                          ------------
    -------------------------------------------------------------------------------

Version3gpp ::= SEQUENCE { 
    majorVersion    INTEGER,
    minorVersion    INTEGER,
    releaseVersion  INTEGER
}

OtaMessageDirection ::= INTEGER {
    upstream (1),
    downstream (2)
}

SystemFrameNumber ::= INTEGER (0..1023)

SubFrameNumber ::= INTEGER (0..9)

ThroughputObject ::= SEQUENCE {
    timeStamp       TimeStamp,
    throughput      INTEGER             --in kbps
}

-- time stamp (Universal Time Coordinated, UTC)
TimeStamp ::= SEQUENCE {
    year    INTEGER,
    month   INTEGER,
    day INTEGER,
    hour    INTEGER,
    minute  INTEGER,
    second  INTEGER,
    millisecond INTEGER
}
-- geographical coordinates of the point
LocationResult ::= CHOICE {
    valid-location  Location,
    location-null   NULL
}
Location ::= SEQUENCE {
        -- all values are double (IETF 754)
    latitude    OCTET STRING(SIZE (8)),
    longitude   OCTET STRING(SIZE (8)),
    altitude    OCTET STRING(SIZE (8))
}

RatInfo ::= INTEGER {
    noService (0),
    gsm (1),
    umts (2),
    lte (3),
    cdma (4),
    wifi (5)
}

CellularRatInfo ::= INTEGER {
    gsm (1),
    umts (2),
    lte (3),
    cdma (4)
}

MCC-MNC ::= SEQUENCE {
    mcc MCC,
    mnc MNC
}
MCC ::= SEQUENCE (SIZE (3)) OF MCC-MNC-Digit
MNC ::= SEQUENCE (SIZE (2..3)) OF MCC-MNC-Digit
MCC-MNC-Digit ::= INTEGER (0..9)

CallStatus ::= INTEGER {
    inactive (0),
    active (1),
    attempting (2),
    hold (3)
}

CallType ::= INTEGER {
    emergency (0),
    voice (1),
    video (2)
}

MCS ::= INTEGER (0..31)

PowerControlAccumalationFactor ::= INTEGER (-141..141)

Earfcn ::= INTEGER (0..262143)

BandIndicator ::= INTEGER (1..64)

PLMN ::= SEQUENCE {
        mccMnc0 MCC-MNC,
        mccMnc1 MCC-MNC,
        mccMnc2 MCC-MNC
}

DciFormat ::= INTEGER {
        format0 (0),
        format1 (1),
        format1A (2),
        format1B (3),
        format1C (4),
        format1D (5),
        format2 (6),
        format2A (7),
        format3 (8),
        format3A (9)
}

PowerValue ::= INTEGER (-112..23)    -- Power measurement in dB

CarrierIndex ::= INTEGER {
    PCC (0),
    SCC1 (1),
    SCC2 (2)
}

CarrierType ::= INTEGER {
    PCC (0),
    SCC (1)
}

DuplexType ::= INTEGER {
    FDD (0),
    TDD (1)
}

ServingCellIndex ::= INTEGER {
    PCell (0),
    SCell1 (1),
    SCell2 (2),
    SCell3 (3),
    SCell4 (4),
    SCell5 (5),
    SCell6 (6),
    SCell7 (7)
}

GmmStateType ::= INTEGER {
    GMM-NULL (1),
    GMM-DEREGISTERED (2),
    GMM-REGISTERED-INITIATED (3),
    GMM-REGISTERED (4),
    GMM-DEREGISTERED-INITIATED (5),
    GMM-ROUTING-AREA-UPDATING-INITIATED (6),
    GMM-SERVICE-REQUEST-INITIATED (7)
}
    
-- GMM sub-state
GmmSubstateType ::= INTEGER(0..9)

-- If GMM state is GMM-DEREGISTERED(2), GMM sub-states
-- GMM-DEREGISTERED.NORMAL-SERVICE (1)
-- GMM-DEREGISTERED.LIMITED-SERVICE (2)
-- GMM-DEREGISTERED.ATTACH-NEEDED (3)
-- GMM-DEREGISTERED.ATTEMPTING-TO-ATTACH (4)
-- GMM-DEREGISTERED.NO-IMSI (5)
-- GMM-DEREGISTERED.NO-CELL-AVAILABLE (6)
-- GMM-DEREGISTERED.PLMN-SEARCH (7)
-- GMM-DEREGISTERED.SUSPENDED (8)


-- If EMM state is GMM-REGISTERED(4), GMM sub-states
-- GMM-REGISTERED.NORMAL-SERVICE (1)
-- GMM-REGISTERED.SUSPENDED (2)
-- GMM-REGISTERED.UPDATE-NEEDED (3)
-- GMM-REGISTERED.ATTEMPTING-TO-UPDATE (4)
-- GMM-REGISTERED.NO-CELL-AVAILABLE (5)
-- GMM-REGISTERED.LIMITED-SERVICE (6)
-- GMM-REGISTERED.ATTEMPTING-TO-UPDATE-MM (7)
-- GMM-REGISTERED.IMSI-DETACH-INITIATED (8)
-- GMM-REGISTERED.PLMN-SEARCH (9)

-- Others use invalid GMM Substate value (0)

MmStateType ::= INTEGER {
    MM-NULL (0),
    MM-LOCATION-UPDATING-INITIATED (3),
    MM-WAIT-FOR-OUTGOING-MM-CONNECTION (5),
    MM-MM-CONNECTION-ACTIVE (6),
    MM-IMSI-DETACH-INITIATED (7),
    MM-PROCESS-CM-SERVICE-PROMPT (8),
    MM-WAIT-FOR-NETWORK-COMMAND (9),
    MM-LOCATION-UPDATE-REJECTED (10),
    MM-WAIT-FOR-RR-CONNECTION-LOCATION-UPDATING (13),
    MM-WAIT-FOR-RR-CONNECTION-MM-CONNECTION (14),
    MM-WAIT-FOR-RR-CONNECTION-IMSI-DETACH (15),
    MM-WAIT-FOR-REESTABLISH (17),
    MM-WAIT-FOR-RR-ACTIVE (18),
    MM-MM-IDLE (19),
    MM-WAIT-FOR-ADDITIONAL-OUTGOING-MM-CONNECTION (20),
    MM-MM-CONNECTION-ACTIVE-GROUP-TRANSMIT-MODE (21),
    MM-WAIT-FOR-RR-CONNECTION-GROUP-TRANSMIT-MODE (22),
    MM-LOCATION-UPDATING-PENDING (23),
    MM-IMSI-DETACH-PENDING (24),
    MM-RR-CONNECTION-RELEASE-NOT-ALLOWED (25)
}

-- MM sub-states
MmSubstateType ::= INTEGER(0..11)

-- If MM state is MM-IDLE(19), MM sub-states
-- MM-IDLE.NORMAL-SERVICE (1)
-- MM-IDLE.ATTEMPTING-TO-UPDATE (2)
-- MM-IDLE.LIMITED-SERVICE (3)
-- MM-IDLE.NO-IMSI (4)
-- MM-IDLE.NO-CELL-AVAILABLE (5)
-- MM-IDLE.LOCATION-UPDATE-NEEDED (6)
-- MM-IDLE.PLMN-SEARCH (7)
-- MM-IDLE.PLMN-SEARCH-NORMAL-SERVICE (8)
-- MM-IDLE.RECEIVING-GROUPCALL-NORMAL-SERVICE (9)
-- MM-IDLE.RECEIVING-GROUPCALL-LIMITED-SERVICE (10)
-- MM-IDLE.CALL-INACTIVE (11)

-- Others use invalid MM Substate value (0)


MmUpdateStatus ::= INTEGER {
    GMM_GU1_UPDATED (0),
    GMM_GU2_NOT_UPDATED (1),
    GMM_GU3_PLMN_NOT_ALLOWED (2),
    GMM_GU3_ROUTING_AREA_NOT_ALLOWED (3)
}

GmmUpdateStatus ::= INTEGER {
    UPDATED (0),
    NOT_UPDATED (1),
    ROAMING_NOT_ALLOWED (2),
    LOCATION_AREA_NOT_ALLOWED (3)
}

    -------------------------------------------------------------------------------
    ------      mdmiDebug                                              ------------
    -------------------------------------------------------------------------------
        -------------------------------------------------------------------------------
        ------      mdmiDebug Config                                       ------------
        -------------------------------------------------------------------------------
-- This log is generated once at the start of a test
deviceName OBJECT-TYPE
    SYNTAX  OCTET STRING
    ACCESS  read-only
    STATUS  mandatory
    DESCRIPTION
    "Human-readable name of the device"
::= {debugConfig 1}

-- This log is generated once at the start of a test
mibVersion OBJECT-TYPE
    SYNTAX  OCTET STRING
    ACCESS  read-only
    STATUS  mandatory
    DESCRIPTION
    "The MIB version that the device supports"
::= {debugConfig 2}

        -------------------------------------------------------------------------------
        ------      mdmiDebug KPIs                                         ------------
        -------------------------------------------------------------------------------

-- This log is generated every 1s
roamingIndicator OBJECT-TYPE
    SYNTAX  RoamingIndicator
    ACCESS  read-only
    STATUS  mandatory
    DESCRIPTION
    "Roaming Indicator"
::= {debugKpis 1}

    RoamingIndicator ::= SEQUENCE {
        inHomeNetwork   BOOLEAN,
        networkName     OCTET STRING,   -- only valid when inHomeNetwork is false
        plmn            PLMN            -- PLMN for home network if inHomeNetwork if true, otherwise, the PLMN for roaming network
    }


        -------------------------------------------------------------------------------
        ------      mdmiDebug Events                                       ------------
        -------------------------------------------------------------------------------

-- This log is generated whenever there is a change in the RAT.
ratEvent OBJECT-TYPE
    SYNTAX  RatInfo
    ACCESS  read-only
    STATUS  mandatory
    DESCRIPTION
    "RAT event"
::= {debugEvents 1}

-- This log is generated whenever the call is connected or disconnected 
callEventWithRAT OBJECT-TYPE
    SYNTAX  CallEventWithRAT
    ACCESS  read-only
    STATUS  mandatory
    DESCRIPTION
    "VoLTE cal event"
::= {debugEvents 2}

    CallEventWithRAT ::= SEQUENCE {
        callStatus      CallStatus,
        callType        CallType,
        ratInfo         RatInfo,
        callDirection   CallDirection
    }

    CallDirection ::= INTEGER {
        MO (0),
        MT (1)
    }

-- This event is reported at the end of "System Determination" procedure. It includes the list of all PLMNs that can be read and scanned during the "System Determination" procedure.
plmnSearchEvent OBJECT-TYPE
    SYNTAX  PlmnSearch
    ACCESS  read-only
    STATUS  mandatory
    DESCRIPTION
    "PLMN Search Info"
::= {debugEvents 3}

    PlmnSearch ::= SEQUENCE OF PlmnScan

    PlmnScan ::= SEQUENCE {
        timeScanStart   TimeStamp,
        timeScanEnd     TimeStamp,
        rat             CellularRatInfo,
        plmn            PLMN,
        bandIndicator   BandIndicator,
        dlEARFCN        Earfcn,
        ulEARFCN        Earfcn
    }

        -------------------------------------------------------------------------------
        ------      mdmiDebug Reserved                                     ------------
        -------------------------------------------------------------------------------

location-fix-result OBJECT-TYPE
    SYNTAX  LocationResult2D
    ACCESS  read-only
    STATUS  mandatory
    DESCRIPTION
    "Latest location fix result"
::= {debugReserved 1}

    LocationResult2D ::= CHOICE {
        valid-location  Location2D,
        location-null   NULL
    }
    Location2D ::= SEQUENCE {
        latitude    OCTET STRING(SIZE (8)), -- Latitude value as double (IETF 754)
        longitude   OCTET STRING(SIZE (8))  -- Longitude value as double (IETF 754)
    }

wifiInfoHLOS OBJECT-TYPE
    SYNTAX  WifiInformation
    ACCESS  read-only
    STATUS  mandatory
    DESCRIPTION
    "WiFi Info"
::= {debugReserved 2}

    WifiInformation ::= SEQUENCE {
        bssid               OCTET STRING,
        ssid                OCTET STRING,
        rssi                OCTET STRING,
        detailState         OCTET STRING,
        supplicantState     OCTET STRING,
        ip                  OCTET STRING,
        linkSpeed           INTEGER,        -- in Mbps
        macAddress          OCTET STRING,
        networkID           OCTET STRING,
        hiddenSSID          OCTET STRING,
        gateway             OCTET STRING,
        netMask             OCTET STRING,
        dns1                OCTET STRING,
        dns2                OCTET STRING,
        serverIP            OCTET STRING
    }

    -------------------------------------------------------------------------------
    ------      mdmiLte RRC                                            ------------
    -------------------------------------------------------------------------------

        -------------------------------------------------------------------------------
        ------      mdmiLte RRC KPIs                                       ------------
        -------------------------------------------------------------------------------

-- MCC/MNC
-- This log is generated every time the serving cell changes and every time there is a SI update
mccMncValue OBJECT-TYPE
    SYNTAX  MCC-MNC
    ACCESS  read-only
    STATUS  mandatory
    DESCRIPTION
    "Value of MCC and MNC"
::= {lteRrcKpis 1}

-- Band Indicator
-- This log is generated every time the serving cell changes and every time there is a SI update
bandIndicatorValue OBJECT-TYPE
    SYNTAX  BandIndicator
    ACCESS  read-only
    STATUS  mandatory
    DESCRIPTION
    "Band Indicator"
::= {lteRrcKpis 2}

-- Downlink Bandwidth
-- This log is generated every time the serving cell changes and every time there is a SI update
dlBandwidthValue OBJECT-TYPE
    SYNTAX  Bandwidth
    ACCESS  read-only
    STATUS  mandatory
    DESCRIPTION
    "Downlink Bandwidth"
::= {lteRrcKpis 3}

    Bandwidth ::= INTEGER {
        Bandwidth-1-4-Mhz (1),  --1.4 MHz
        Bandwidth-3-Mhz (2),    --3 MHz
        Bandwidth-5-Mhz (3),    --5 MHz
        Bandwidth-10-Mhz (4),   --10 MHz
        Bandwidth-15-Mhz (5),   --15 MHz
        Bandwidth-20-Mhz (6)    --20 MHz
    }

-- Uplink Bandwidth
-- This log is generated every time the serving cell changes and every time there is a SI update
ulBandwidthValue OBJECT-TYPE
    SYNTAX  Bandwidth
    ACCESS  read-only
    STATUS  mandatory
    DESCRIPTION
    "Uplink Bandwidth"
::= {lteRrcKpis 4}

-- Downlink Frequency
-- This log is generated every time the serving cell changes and every time there is a SI update
dlFrequencyValue OBJECT-TYPE
    SYNTAX  Earfcn
    ACCESS  read-only
    STATUS  mandatory
    DESCRIPTION
    "Downlink Frequency as EARFCN"
::= {lteRrcKpis 5}

-- Uplink Frequency
-- This log is generated every time the serving cell changes and every time there is a SI update
ulFrequencyValue OBJECT-TYPE
    SYNTAX  Earfcn
    ACCESS  read-only
    STATUS  mandatory
    DESCRIPTION
    "Uplink Frequency as EARFCN"
::= {lteRrcKpis 6}

-- This log is generated every time the serving cell changes and every time there is a SI update.
trackingAreaCode OBJECT-TYPE
    SYNTAX  TrackingAreaCode
    ACCESS  read-only
    STATUS  mandatory
    DESCRIPTION
    "Tracking area code"
::= {lteRrcKpis 7}

    TrackingAreaCode ::= INTEGER(0..65535)      -- the unique code that each operator assigns to each of their Tracking Areas (TAs)

-- Cell Identity - from RRC SIB
-- This log is generated every time the serving cell changes and every time there is a SI update
cellIdValue OBJECT-TYPE
    SYNTAX  CellId
    ACCESS  read-only
    STATUS  mandatory
    DESCRIPTION
    "Cell Identity"
::= {lteRrcKpis 8}

    CellId ::= INTEGER (0..268435455)

        -------------------------------------------------------------------------------
        ------      mdmiLte RRC Events                                     ------------
        -------------------------------------------------------------------------------

-- This log is generated when there is a cell reselection event
cellReselectionEvent OBJECT-TYPE
    SYNTAX  CellReselectionEventType
    ACCESS  read-only
    STATUS  mandatory
    DESCRIPTION
    "Events relating to Cell Reselection"
::= {lteRrcEvents 1}

    CellReselectionEventType ::= CHOICE {
        cellReselectionAttempt  NULL,
        cellReselectionFailure  CellReselectionFailure
    }

    CellReselectionFailure ::= SEQUENCE {
        dlArfcn                                 Earfcn,
        cellId                                  INTEGER,
        failureType                             CellReselectionFailureType
    }

    CellReselectionFailureType ::= INTEGER {
        S-Failure (1),                  -- S criteria failure. refer to ETSI TS 136 304 V13.0.0 (2016-02)
        Sib-Read-Failure (2),           -- Cell found, S criteria found, but SIB/MIB read failure
        Weak-Downlink-Indicator (3),    -- if UE is unable to find two down link synchronization signals (PSS & SSS) due to weak perceived down link signal.
        Cell-Barred (4),
        Non-Valid-Plmn (5),
        Forbidden-Tracking-Area (6),
        Aborted (7),
        Forbidden-CSG-Id (8),
        IRAT-Reselection-Failure (9),
        Frequency-Barred (10)
    }

-- This log is generated when there is a handover event
handoverEvent OBJECT-TYPE
    SYNTAX  HandoverEventType
    ACCESS  read-only
    STATUS  mandatory
    DESCRIPTION
    "Events relating to Handover"
::= {lteRrcEvents 2}

    HandoverEventType ::= SEQUENCE {
        handoverResult      HandoverResult,
        targetCell          TargetCell
    }
    
    TargetCell ::= SEQUENCE {
        earfcn                 Earfcn,                 -- EARFCN
        physicalCellID         INTEGER (0..504),       -- Physical Cell ID
        targetCellRsrp         INTEGER (-180..-30)      -- Target cell RSRP in dBm
    }

    HandoverResult ::= CHOICE {
        handoverSuccess NULL,
        handoverFailure HandoverFailure
    }

    HandoverFailure ::= SEQUENCE {
        dlArfcn             Earfcn,
        cellId              INTEGER,
        failureType         HandoverFailureType
    }

    HandoverFailureType ::= INTEGER {
        Other (1),                  -- Other reason instead of reason below
        InvalidCfg (2),             -- Validation failure
        PhysicalFailure (3),        -- Physical layer failure on the target cell
        Rach (4),                   -- T304 expiry due to RACH failure on target cell
        RachMeasConfigIncluded (5)  -- T304 expiry due to RACH failure on target cell when MeasConfig IE was included
    }

-- This log is generated when UE detects RLF
radioLinkFailureEvent OBJECT-TYPE
    SYNTAX  RadioLinkFailureEvent
    ACCESS  read-only
    STATUS  mandatory
    DESCRIPTION
    "Event indicating Radio Link Failure"
::= {lteRrcEvents 3}

    RadioLinkFailureEvent ::= SEQUENCE {
        rlfCounter      RadioLinkFailureEventCounter,          -- Counter to show how many times UE has detected RLF since UE entered RRC CONNECTED state
        rlfCause        RlfCause,                              -- RLF cause
        rlfCauseOther   OCTET STRING(SIZE (0..20))             -- RLF cause other only valid when rlfCause = 7
    }

    RadioLinkFailureEventCounter ::= INTEGER (1..255)

    RlfCause ::= INTEGER {
        configurationFailue(0),
        handoverFailure(1),
        rachFailure(2),
        maxRetransmission(3),
        ipCheckFailue(4),
        sibReadingFailure(5),
        mibChange(6),
        other(7)
    }

-- This log is generated when UE transition to a new cell
newCellEvent OBJECT-TYPE
    SYNTAX  NewCellEventType
    ACCESS  read-only
    STATUS  mandatory
    DESCRIPTION
    "This Event is logged when UE transition to a new cell"
::= {lteRrcEvents 4}

    NewCellEventType ::= SEQUENCE {
        cause   NewCellCause,
        campedStatus    NewCellStatus
    }
    NewCellCause ::= INTEGER {
        cellSelection (1),
        cellReselection (2),
        handover (3),
        redirection (4)
    }
    NewCellStatus   ::= INTEGER {
        suitable (1),
        acceptable (2)
    }

-- This log is generated every time there is RRC state change
rrcStateChangeEvent OBJECT-TYPE
    SYNTAX  RrcStateChangeEvent
    ACCESS  read-only
    STATUS  mandatory
    DESCRIPTION
    "RRC state change event"
::= {lteRrcEvents 5}
    
    RrcStateChangeEvent ::= SEQUENCE {
        rrcState                RrcState,               -- RRC state
        rrcStateChangeCause     RrcStateChangeCause     -- Trigger for RRC state change
    }
    
    RrcState ::= INTEGER {
        null(0),
        idleCampedOnAnyCell(1),
        idleCampedNormally(2),
        idlConnecting(3),
        connectedNormally(4),
        releasing(5)            -- when going from connected to idle
    }
    
    -- Note that cause codes are defined only when a transition from a stable to stable state happens.
    RrcStateChangeCause ::= INTEGER {
        toNull (0),                         -- Generic cause for all state transitions to null state. From any stable state other than null to null state.
        IdleFromUpperLayer (1),             -- Camped due to connection aborted from upper layers. From any stable state to idlecampednormally.
        idleT300Expiry (2),                 -- Camped due to T300expiry. From any stable state other than connectednormally to idlecampednormally.
        idleConnectionReject (3),           -- Camped due to connection rejected from eNB. From any stable state other than connectednormally to idlecampednormally.
        idleCellReselectionFailure (4),     -- Camped due to cell reselection. From idlecampednormally to idlecampednormally.
        idleBarred (5),                     -- Camped due to access barring. From any stable state to idlecampednormally.
        idleOtherRrcFailue (6),             -- Camped due to other reasons. From any stable state to idlecampednormally.
        idleEnteringLte (7),                -- From null to idlecampednormally.
        connectingEmergencyCall (8),        -- Enter connecting due to emergency call. Any stable state other than connectednormally to connectednormally
        connectingHighPriAccess (9),        -- Enter connecting due to high priority access. From idlecampednormally to connectednormally.
        connectingReceiveCall (10),         -- Enter connecting due to receiving call. From idlecampednormally to connectednormally.
        connectingMakingCall (11),          -- Enter connecting due to making call. From idlecampednormally to connectednormally.
        connectingMoData (12),              -- Enter connecting due to originating a data session. From idlecampednormally to connectednormally.
        embmsFileRepair (13),               -- From idleCampedNormaly to connectedNormally.
        embmsReceptionReport(14),           -- From idleCampedNormaly to connectedNormally.
        connectingVolteCall (15),           -- Enter connecting due to VoLTE call. From idlecampednormally to connectednormally.
        connectedHoFailure (16),            -- Camped on a cell in connected state due to handover failure. From connectednormally to idlecampednormally or idlecampedonanycell.
        connectedOther (17),                -- Camped on a cell in connected state due to other reasons. From connectednormally to idlecampednormally or idlecampedonanycell.
        releasingT311Expriry (18),          -- Enter releasing due to T311 expiry. From connected normally to idlecampednormally.
        releasingT301Expriry (19),          -- Enter releasing due to T301 expiry. From connected normally to idlecampednormally.
        releasingReject (20),               -- Enter releasing due to RRC connection reestablishment reject. From connected normally to idlecampednormally.
        connectingOther (21)                -- From idlecampednormally to connectednormally for other procedures like Extended service request, TAU, or RRC reestablishment
    }

-- This log is generated every time a rrc timer expires.
rrcTimerExpiryEvent OBJECT-TYPE
    SYNTAX  RrcTimerExpiryEvent
    ACCESS  read-only
    STATUS  mandatory
    DESCRIPTION
    "RRC timer expiry event"
::= {lteRrcEvents 6}
    
    RrcTimerExpiryEvent ::= INTEGER {
        t300(1),
        t301(2),
        t302(3),
        t303(4),
        t304(5),
        t305(6),
        t311(7),
        t320(8),
        t321(9),
        other(10)
    }

-- This log is generated when there are MIB and SIBs to read
mibSibReadEvent OBJECT-TYPE
    SYNTAX  MibSibReadEvent
    ACCESS  read-only
    STATUS  mandatory
    DESCRIPTION
    "MIB and SIB read event"
::= {lteRrcEvents 7}

    MibSibReadEvent ::= CHOICE {
        readSuccess         MibSibContent,     -- read MIB or SIB messages successfully, either entirely or partialy
        readFail            NULL               -- fail to read MIB or SIB messages entirely
    }
    
    MibSibContent ::= SEQUENCE {
        mibContent              CHOICE {            -- MIB content
            mibContent-Null     NULL,               -- Report null when not available
            mibContent          MibContent
        },
        sibInfo                 CHOICE {            -- SIB Information
            sibInfo-Null        NULL,               -- Report null when not available
            sibInfo             SibInfo             
        }                 
    }

    SibInfo ::= SEQUENCE {
        systemInfoMask          SEQUENCE OF SibType,    -- List of SIB types mapped to systeminformation message, refer to "SIB-MappingInfo" in 3GPP TS 36.331. Only applicable to SIB1 message, for all other SIB messages, report a SEQUENCE with no element
        systemInfoMsgNum        INTEGER (1..10),        -- Total number of different SIBs received by UE all together, count multiple SIBs when more than one SIBs with the same type is read
        sibMask                 INTEGER                 -- Bit mask for one or more SIB types which were successfully read (Bit 0 for SIB 1, Bit 1 for SIB 2, ...). For example, if sibMask=11, the binary format is 1011, which means SIB1, SIB2, SIB4 were read.    
    }

    SibType ::= INTEGER {
        sib2 (2),
        sib3 (3),
        sib4 (4),
        sib5 (5),
        sib6 (6),
        sib7 (7),
        sib8 (8),
        sib9 (9),
        sib10 (10),
        sib11 (11),
        sib12 (12),
        sib13 (13),
        sib14 (14),
        sib15 (15),
        sib16 (16),
        sib17 (17),
        sib18 (18),
        sib19 (19)
    }

    MibContent ::= SEQUENCE {
        pci         INTEGER (0..504),           -- pci
        freq        Earfcn,                     -- EARFCN
        antennas    INTEGER,                    -- Number of Tx antennas detected
        bandwidth   Bandwidth                   -- Downlink bandwidth
    }

-- This log is generated when UE detects out of service area
outOfServiceEvent OBJECT-TYPE
    SYNTAX  OutOfServiceCounter
    ACCESS  read-only
    STATUS  mandatory
    DESCRIPTION
    "Out Of Service"
::= {lteRrcEvents 9}

    OutOfServiceCounter ::= INTEGER

-- This log is generated when MobilityFromE-UTRAN procedure starts
mobilityFromEutranStartEvent OBJECT-TYPE
    SYNTAX  MobilityFromEutranStart
    ACCESS  read-only
    STATUS  mandatory
    DESCRIPTION
    "Mobility from EUTRAN start"
::= {lteRrcEvents 10}

    MobilityFromEutranStart ::= INTEGER {
        UTRA_HO(0),
        GERAN_HO(1),
        GERAN_Cell_Change_Order(2)
    }

-- This log is generated when MobilityFromE-UTRAN procedure fails
mobilityFromEutranFailedEvent OBJECT-TYPE
    SYNTAX  MobilityFromEutranFailed
    ACCESS  read-only
    STATUS  mandatory
    DESCRIPTION
    "Mobility from EUTRAN fails"
::= {lteRrcEvents 11}

    MobilityFromEutranFailed ::= INTEGER {
        Protocol_error(0),
        Configuration_error(1),
        Physical_channel_error(2),
        Invalid_frequency(3),
        Invalid_message(4),
        other(5)
    }

-- This log is generated when SIB reading fails
sibReadFailureEvent OBJECT-TYPE
    SYNTAX  SibReadFailure
    ACCESS  read-only
    STATUS  mandatory
    DESCRIPTION
    "SIB read failure"
::= {lteRrcEvents 12}

    SibReadFailure ::= SEQUENCE {
        dlArfcn             Earfcn,
        cellId              INTEGER,
        receivedSibBitmask  INTEGER
    }

-- This log is generated when UE detects out of service eMBMS area and services are unavailable
embmsOutOfServiceEvent OBJECT-TYPE
    SYNTAX  EmbmsOutOfService
    ACCESS  read-only
    STATUS  mandatory
    DESCRIPTION
    "eMBMS Out of Service"
::= {lteRrcEvents 13}

    EmbmsOutOfService ::= SEQUENCE {
        affectedServices        SEQUENCE OF EmbmsService,
        affectedAreas           SEQUENCE OF EmbmsArea
    }

    EmbmsService ::= SEQUENCE {
        plmnIdInTmgi            INTEGER,
        serviceIdInTmgi         INTEGER,
        sessionId               INTEGER,
        mrbId                   INTEGER
    }

    EmbmsArea ::= SEQUENCE {
        mbsfnAreaId             INTEGER
    }

-- This log is generated when UE black lists a cell
cellBlacklistEvent OBJECT-TYPE
    SYNTAX  CellBlacklist
    ACCESS  read-only
    STATUS  mandatory
    DESCRIPTION
    "Cell blacklist"
::= {lteRrcEvents 14}

    CellBlacklist ::= SEQUENCE {
        dlArfcn         Earfcn,
        cellId          INTEGER
    }

-- This log is generated when carrier aggregation configuration and deconfiguration occurs
caConfigurationEvent OBJECT-TYPE
    SYNTAX  BOOLEAN
    ACCESS  read-only
    STATUS  mandatory
    DESCRIPTION
    "CA Configuration"
::= {lteRrcEvents 15}

-- This log is generated when UE starts cell reselection procedure
cellReselectionStartEvent OBJECT-TYPE
    SYNTAX  CellReselectionStart
    ACCESS  read-only
    STATUS  mandatory
    DESCRIPTION
    "Cell Reselection Start"
::= {lteRrcEvents 16}

    CellReselectionStart ::= SEQUENCE {
        dlarfcn                 Earfcn,
        cellId                  INTEGER
    }

-- This log is generated whenever a Measurement Report uplink message is sent by UE
measurementReportEvent OBJECT-TYPE
    SYNTAX  MeasurementReport  
    ACCESS  read-only
    STATUS  mandatory
    DESCRIPTION
    "Measurement Report"
::= {lteRrcEvents 17}

    MeasurementReport ::= SEQUENCE {
        ratType             RatType
    }

    RatType ::= INTEGER {
        EUTRA(0),
        UTRA(1),
        GERAN(2),
        CDMA(3)
    }

-- This log is generated whenever a status change related to a RRC timer occurs
rrcTimerStatusEvent OBJECT-TYPE
    SYNTAX  RrcTimerStatus
    ACCESS  read-only
    STATUS  mandatory
    DESCRIPTION
    "RRC Timer Status"
::= {lteRrcEvents 18}

    RrcTimerStatus ::= SEQUENCE {
        timerName           RrcTimerName,
        timerValue          INTEGER,
        timerStatus         TimerStatus
    }

    RrcTimerName ::= INTEGER {
        T300(0),
        T301(1),
        T302(2),
        T303(3),
        T304(4),
        T305(5),
        T306(6),
        T307(7),
        T310(8),
        T311(9),
        T312(10),
        T313(11),
        T320(12),
        T321(13),
        T325(14),
        T330(15),
        T340(16),
        T350(17)
    }

    TimerStatus ::= INTEGER {
        Started(0),
        Stopped(1),
        Expired(2)
    }

        -------------------------------------------------------------------------------
        ------      mdmiLte RRC Messages                                   ------------
        -------------------------------------------------------------------------------

-- RRC OTA Message from 3GPP 36.331
rrc-OTA-Message OBJECT-TYPE
    SYNTAX  RrcMessageReport
    ACCESS  read-only
    STATUS  mandatory
    DESCRIPTION
    "RRC OTA Message - most recent."
::= {lteRrcMessages 1}

    RrcMessageReport ::= SEQUENCE {
        rrc-version Version3gpp,
        pdu-type    RrcPduType,
        rrcPayload  OCTET STRING(SIZE (1..8192))
    }
    -- PDU Types for RRC messages (must be known to decode payload)
    RrcPduType ::= INTEGER {
        pcch (1),
        dlCcch (2),
        dlDcch (3),
        ulCcch (4),
        ulDcch (5),
        mcch (6),
        bcchDlSch (7)
    }

    -------------------------------------------------------------------------------
    ------      mdmiLte NAS                                            ------------
    -------------------------------------------------------------------------------
        -------------------------------------------------------------------------------
        ------      mdmiLte NAS KPIs                                       ------------
        -------------------------------------------------------------------------------

-- This log record is generated when NAS bearer context is modified
esmContextInfo OBJECT-TYPE
    SYNTAX  EsmContextInfo
    ACCESS  read-only
    STATUS  mandatory
    DESCRIPTION
    "Information about the ESM context state"
::= {lteNasKpis 1}

    EsmContextInfo ::= SEQUENCE {
        contextType         ContextType,
        bearerId            INTEGER,        -- ID of the bearer context
        bearerState         BearerState,    -- Bearer State
        radioBearerId       INTEGER,        -- Radio bearer ID corresponding to EPS Bearer ID of the context
        epsQos              EpsQos,
        connectionId        INTEGER,
        serviceDataFlowId   INTEGER,
        linkedEpsBearerId   INTEGER
    }

    EpsQos ::= SEQUENCE {
        qci                 INTEGER,        -- QoS Class Identifier (TS 23.203)
        maxUlBitRate        INTEGER,
        maxDlBitRate        INTEGER,
        ulGbr               INTEGER,
        dlGbr               INTEGER
    }

    ContextType ::= INTEGER {
        default (0),
        dedicated (1)
    }
    
    BearerState ::= INTEGER {
        null (0),
        activeWaiting (1),
        active (2),
        modifying (3)
    }

        -------------------------------------------------------------------------------
        ------      mdmiLte NAS Events                                     ------------
        -------------------------------------------------------------------------------

-- EMM state and sub-state
-- This log is generated every time the EMM state changes
emmStateValue OBJECT-TYPE
    SYNTAX  EmmStates
    ACCESS  read-only
    STATUS  mandatory
    DESCRIPTION
    "Current EMM State and Substate"
::= {lteNasEvents 1}

    -- Refer to 3GPP TS 24.301 Section 5.1.3.2 for more details
    EmmStates ::= SEQUENCE {
        emmState        EmmStateType,
        emmSubstate     EmmSubstateType
    }

    -- EMM State Values
    EmmStateType ::= INTEGER {
        EmmNull (1),
        EmmDeregistered (2),
        EmmRegisteredInitiated (3),
        EmmRegistered (4),
        EmmTrackingAreaUpdatingInitiated (5),
        EmmServiceRequestInitiated (6),
        EmmDeregisteredInitiated (7)
    }
    
    -- EMM sub-state
    EmmSubstateType ::= INTEGER(0..8)
    
    -- If EMM state is EmmDeregistered(2), EMM sub-state
    -- EmmDeregisteredNoImsi(1)
    -- EmmDeregisteredPlmnSearch(2)
    -- EmmDeregisteredAttachNeeded(3)
    -- EmmDeregisteredNoCellAvailable(4)
    -- EmmDeregisteredAttemptingToAttach(5)
    -- EmmDeregisteredNormalService(6)
    -- EmmDeregisteredLimitedService(7)
    
    
    -- If EMM state is EmmRegistered(4), EMM sub-state
    -- EmmRegisteredNormalService(1)
    -- EmmRegisteredUpdateNeeded(2)
    -- EmmRegisteredAttemptingToUpdate(3)
    -- EmmRegisteredNoCellAvailable(4)
    -- EmmRegisteredPlmnSearch(5)
    -- EmmRegisteredLimitedService(6)
    -- EmmRegisteredImsiDetachInitiated(7)
    -- EmmRegisteredAttemptingToUpdateMm(8)

    -- Others use invalid EMM Substate value (0)

-- This log is generated when a EMM timer expired.
nasEmmTimerExpiryEvent OBJECT-TYPE
    SYNTAX  NasEmmTimerExpiryEvent
    ACCESS  read-only
    STATUS  mandatory
    DESCRIPTION
    "NAS EMM timer exspiry event"
::= {lteNasEvents 2}
    
    NasEmmTimerExpiryEvent ::= INTEGER {
        t3410(1)
    }

-- This log is generated every time there is a NAS ESM timer expires
nasEsmExpiryEvent OBJECT-TYPE
    SYNTAX  NasEsmExpiryEvent
    ACCESS  read-only
    STATUS  mandatory
    DESCRIPTION
    "NAS ESM expiry event"
::= {lteNasEvents 3}
    
    NasEsmExpiryEvent ::= INTEGER {
        t3480(1),
        t3482(2),
        t3481(3),
        t3492(4)
    }

-- This log is generated every time UE receives ATTACH REJECT NAS Message
-- For detailed enumeration of EMM Causes, please refer to 3GPP 24.301
emmFailureCauseEvent OBJECT-TYPE
    SYNTAX  EMMCause
    ACCESS  read-only
    STATUS  mandatory
    DESCRIPTION
    "EMM Cause within NAS ATTACH REJECT Message"
::= {lteNasEvents 4}

    EMMCause ::= INTEGER(0 .. 255)

        -------------------------------------------------------------------------------
        ------      mdmiLte NAS Messages                                   ------------
        -------------------------------------------------------------------------------

-- NAS Messages from 3GPP 24.301
nas-OTA-Message OBJECT-TYPE
    SYNTAX  NasMessageReport
    ACCESS  read-only
    STATUS  mandatory
    DESCRIPTION
    "NAS OTA Message - most recent."
::= {lteNasMessages 1}

    NasMessageReport ::= SEQUENCE {
        nas-version Version3gpp,
        direction   OtaMessageDirection,
        type    NasMessageType,
        ciphered    BOOLEAN,
        nasPayload  OCTET STRING(SIZE (1..8192))
    }
    NasMessageType ::= INTEGER {
        esm (1),
        emm (2)
    }

    -------------------------------------------------------------------------------
    ------      mdmiLte MAC                                            ------------
    -------------------------------------------------------------------------------
        -------------------------------------------------------------------------------
        ------      mdmiLte MAC KPIs                                       ------------
        -------------------------------------------------------------------------------

macThroughputDL OBJECT-TYPE
-- Downlink throughput measured by the UE during an ftp-download session, on the MAC sub-layer
-- MAC from 3GPP TS 36.321
--http://www.etsi.org/deliver/etsi_ts/136300_136399/136321/12.05.00_60/ts_136321v120500p.pdf
    SYNTAX  ThroughputObject
    ACCESS  read-only
    STATUS  mandatory
    DESCRIPTION
    "Downlink throughput measured by the UE on the MAC sub-layer. Object is time-stamped and geo-referenced."
::= {lteMacKpis 1}

macThroughputUL OBJECT-TYPE
-- Uplink throughput measured by the UE during an ftp-download session, on the MAC sub-layer
-- MAC from 3GPP TS 36.321
--http://www.etsi.org/deliver/etsi_ts/136300_136399/136321/12.05.00_60/ts_136321v120500p.pdf
    SYNTAX  ThroughputObject
    ACCESS  read-only
    STATUS  mandatory
    DESCRIPTION
    "Uplink throughput measured by the UE on the MAC sub-layer. Object is time-stamped and geo-referenced."
::= {lteMacKpis 2}

-- This log is generated every 1s
rachLatency OBJECT-TYPE
    SYNTAX  RachLatency
    ACCESS  read-only
    STATUS  mandatory
    DESCRIPTION
    "RACH Latency"
::= {lteMacKpis 3}

    RachLatency ::= SEQUENCE {
        sysFrameNumber    SystemFrameNumber,
        subFrameNumber    SubFrameNumber,
        rachLatencyVal    INTEGER           -- time in ms between 1st preamble and response from NW in DL
    }

-- This log is generated every 1s
ulRACHAccessDelayValue OBJECT-TYPE
    SYNTAX  Delay
    ACCESS  read-only
    STATUS  mandatory
    DESCRIPTION
    "Average time required to reach a successful attempt during the sampling period"
::= {lteMacKpis 4}

    Delay ::= SEQUENCE {
        sysFrameNumber    SystemFrameNumber,
        subFrameNumber    SubFrameNumber,
        delay             INTEGER           -- time in ms
    }

-- This log is generated every 100ms
macDlTransportBlock OBJECT-TYPE
    SYNTAX  MacDlTransportBlocks
    ACCESS  read-only
    STATUS  mandatory
    DESCRIPTION
    "MAC DL Transport block"
::= {lteMacKpis 5}

    MacDlTransportBlocks ::= SEQUENCE OF MacDlTransportBlock

    MacDlTransportBlock ::= SEQUENCE {
        sysFrameNumber      SystemFrameNumber,
        subFrameNumber      SubFrameNumber,
        rntiType            RntiType,
        harqId              INTEGER,
        numRlcPdus          INTEGER,
        numPaddingBytes     INTEGER,
        macHeader           OCTET STRING(SIZE (0..32)),
        tb                  INTEGER            -- Total transport block size assigned to the UE for data reception on the DL
    }
    
-- This log is generated every 500 ms
macUlGrant OBJECT-TYPE
    SYNTAX  MacUlGrant
    ACCESS  read-only
    STATUS  mandatory
    DESCRIPTION
    "MAC UL grant"
::= {lteMacKpis 6}

    MacUlGrant ::= SEQUENCE {
        sysFrameNumber    SystemFrameNumber,
        subFrameNumber    SubFrameNumber,
        ulGrant           INTEGER,            -- Uplink grant size in bytesreception on the DL
        paddingBytes      INTEGER
    }

-- This log is generated when Scheduling Request Period changes
srPeriodChangeEvent OBJECT-TYPE
    SYNTAX  SrPeriod
    ACCESS  read-only
    STATUS  mandatory
    DESCRIPTION
    "Scheduling Request Period Change Event"
::= {lteMacKpis 7}

    SrPeriod ::= SEQUENCE {
        sysFrameNumber                      SystemFrameNumber,
        subFrameNumber                      SubFrameNumber,
        schedulingRequestPeriodValue        INTEGER            -- Scheduling Request Period in ms
    }

-- This log is generated every 100ms
macUlTransportBlock OBJECT-TYPE
    SYNTAX  MacUlTransportBlocks
    ACCESS  read-only
    STATUS  mandatory
    DESCRIPTION
    "MAC UL Transport block"
::= {lteMacKpis 8}

    MacUlTransportBlocks ::= SEQUENCE OF MacUlTransportBlock

    MacUlTransportBlock ::= SEQUENCE {
        sysFrameNumber      SystemFrameNumber,
        subFrameNumber      SubFrameNumber,
        rntiType            RntiType,
        ulGrant             INTEGER,
        harqId              INTEGER,
        numRlcPdus          INTEGER,
        numPaddingBytes     INTEGER,
        macHeader           OCTET STRING(SIZE (0..32)),
        bsrTriggerCause     BsrTriggerCause,
        bsrType             BsrType
    }

    BsrTriggerCause ::= INTEGER {
        None(0),
        Periodic(1),
        HighDataArrival(2),
        RobustnessBsr(3)
    }

    BsrType ::= INTEGER {
        NoBsr(0),
        Cancelled(1),
        LongBsr(2),
        ShortBsr(3),
        PaddingLongBsr(4),
        PaddingShortBsr(5),
        PaddingTruncatedBsr(6)
    }

-- This log is generated every 100ms
macUlTxStatistics OBJECT-TYPE
    SYNTAX  MacUlTxStatistics
    ACCESS  read-only
    STATUS  mandatory
    DESCRIPTION
    "MAC UL Tx Statistics"
::= {lteMacKpis 9}

    MacUlTxStatistics ::= SEQUENCE {
        numPaddingBsr               INTEGER,
        numNormalBsr                INTEGER,
        numPeriodicBsr              INTEGER,
        numCancelledBsr             INTEGER,
        receivedGrantBytes          INTEGER,
        usedGrantBytes              INTEGER
    }

        -------------------------------------------------------------------------------
        ------      mdmiLte MAC Events                                     ------------
        -------------------------------------------------------------------------------

-- This log is generated when there is a RACH attempt
macRachAttemptEvent OBJECT-TYPE
    SYNTAX  MacRachAttempt
    ACCESS  read-only
    STATUS  mandatory
    DESCRIPTION
    "Events relating to MAC RACH Attempt"
::= {lteMacEvents 1}

    MacRachAttempt ::= SEQUENCE {
        rachAttemptCounter              INTEGER,
        rachResult                      MacRachAttemptEventType,
        contentionBased                 BOOLEAN,
        rachMessage                     INTEGER(0..2),              -- 0: MSG 1, 1: MSG 2, 2: MSG 3
        preambleIndex                   INTEGER(0..63),             -- preambleIndex=There are 64 preambles available in each cell. Range is from 0-63. (3GPP 36.211)
        preamblePowerOffset             INTEGER,                    -- preamblePowerOffset= stepsize*preamble transmission number
        backoffTime                     INTEGER,
        msg2Result                      BOOLEAN,
        msg2TemporaryCrnti              INTEGER,
        timingAdjustmentValue           INTEGER,
        msg3Grant                       INTEGER,
        harqId                          INTEGER,
        msg3MacPdu                      OCTET STRING(0..10)         -- MAC header, MAC CEs, and CCCH message for msg3MacPdu field are mandatory, whereas RLC PDUs for msg3MacPdu is optional
    }

    MacRachAttemptEventType ::= INTEGER {
        Success (0),                                        -- Success
        Failure-At-Msg-2 (1),                               -- Failure at MSG2
        Failure-At-Msg-4-CT-Timer-Expired (2),              -- Failure at MSG4 due to CT timer expired
        Failure-At-Msg-4-CT-Resolution-Not-Passed (3),      -- Failure at MSG4 due to CT resolution is not passed
        Aborted (4)                                         -- Aborted
    }

-- This log is generated when there is a RACH attempt
macRachAttemptReasonEvent OBJECT-TYPE
    SYNTAX  MacRachAttemptReason
    ACCESS  read-only
    STATUS  mandatory
    DESCRIPTION
    "This Event gives the reason for a RACH attempt."
::= {lteMacEvents 2}

    MacRachAttemptReason ::= SEQUENCE {
        reason                      MacRachAttemptReasonType,
        ueId                        INTEGER,
        contention                  BOOLEAN,
        preamble                    INTEGER,                    -- preamble= The random access preambles are generated from Zadoff-Chu sequences with zero correlation zone (3GPP TS 36.211)
        preambleRaIndex             INTEGER(0..15),             -- preambleRA Index= ra-PRACH-MaskIndex or PRACH Mask Index. Range is from 0-15 (3GPP 36.321)
        msg3Size                    INTEGER,
        preambleGroupChosen         INTEGER(0..1),              -- 0: Group A, 1: Group B
        ueCrnti                     INTEGER                     
    }

    MacRachAttemptReasonType ::= INTEGER {
        Connection-Request (1),
        Radio-Link-Failure (2),
        UL-Data-Arrival (3),
        DL-Data-Arrival (4),
        Handover (5)
    }

-- This log is generated every time there is a MAC timer expires
macTimerExpiryEvent OBJECT-TYPE
    SYNTAX  MacTimerExpiryEvent
    ACCESS  read-only
    STATUS  mandatory
    DESCRIPTION
    "MAC timer expiry event"
::= {lteMacEvents 3}
    
    MacTimerExpiryEvent ::= INTEGER {
        timeAlignmentTimer(1),  -- Time Alignment Timer
        randomAccessTimer(2),   -- Random Access Timer
        contentionTimer(3),     -- Contention Timer
        rachBackOffTimer(4)     -- RACH BackOFF Timer
    }

-- This log is generated every time MAC is reset
macResetEvent OBJECT-TYPE
    SYNTAX  MacResetCause
    ACCESS  read-only
    STATUS  mandatory
    DESCRIPTION
    "MAC Reset"
::= {lteMacEvents 4}

    MacResetCause ::= INTEGER {
        Other(0),
        ConnectionRelease(1),
        Handover(2),
        RadioLinkFailure(3)
    }

-- This log is generated every time MAC is configured by RRC
macConfigurationEvent OBJECT-TYPE
    SYNTAX  MacConfiguration
    ACCESS  read-only
    STATUS  mandatory
    DESCRIPTION
    "MAC Configuration"
::= {lteMacEvents 5}

    MacConfiguration ::= SEQUENCE {
        cause               MacConfigurationCause,
        taTimer             INTEGER
    }

    MacConfigurationCause ::= INTEGER {
        Normal(0),
        Handover(1),
        ConnectionRelease(2),
        RLF(3)
    }

-- This log is generated every time MAC is configured by RRC
macRachConfigurationEvent OBJECT-TYPE
    SYNTAX  MacRachConfiguration
    ACCESS  read-only
    STATUS  mandatory
    DESCRIPTION
    "MAC RACH Configuration"
::= {lteMacEvents 6}

    MacRachConfiguration ::= SEQUENCE {
        preambleInitialPower                INTEGER,                    -- in unit dB
        stepPower                           INTEGER(0..255),            -- in unit dB
        groupAPreambleIndex                 INTEGER(1..64),
        groupBPreambleIndex                 INTEGER(1..64),
        maxPreambleAttempts                 INTEGER,
        contentionResolutionTimerValue      INTEGER,
        groupAPreambleSelectionThreshold    INTEGER,
        groupBPowerOffset                   INTEGER,                    -- in unit dB
        pmax                                INTEGER,                    -- in unit dB
        deltaPreamblePowerMsg3              INTEGER,                    -- in unit dB
        preambleCyclicShift                 INTEGER,
        logicalRootZadoffChuSeqNumber       INTEGER,
        prachFreqOffsetMsg1                 INTEGER,
        rachHighSpeedFlag                   INTEGER,
        maxRetxMsg3                         INTEGER,
        rarWindowSize                       INTEGER
    }

-- This log is generated every time MAC is configured by RRC
macUlConfigurationEvent OBJECT-TYPE
    SYNTAX  MacUlConfiguration
    ACCESS  read-only
    STATUS  mandatory
    DESCRIPTION
    "MAC UL Configuration"
::= {lteMacEvents 7}

    MacUlConfiguration ::= SEQUENCE {
        schedulingRequestPeriodPresent              BOOLEAN,
        periodicBsrTimer                            INTEGER,
        retxBsrTimer                                INTEGER
    }

-- This log is generated after each RACH attempt
macTimerStatusEvent OBJECT-TYPE
    SYNTAX  MacTimerStatus
    ACCESS  read-only
    STATUS  mandatory
    DESCRIPTION
    "MAC Timer Status"
::= {lteMacEvents 8}

    MacTimerStatus ::= SEQUENCE {
        timerName           MacTimerName,
        timerStatus         TimerStatus
    }

    MacTimerName ::= INTEGER {
        TA(1),
        RA(2),
        Contention(3),
        RACH_Back_Off(4)
    }

-- This log is generated whenever the timing advance control element is received
macTimingAdvanceEvent OBJECT-TYPE
    SYNTAX  MacTimingAdvance
    ACCESS  read-only
    STATUS  mandatory
    DESCRIPTION
    "MAC Timing Advance"
::= {lteMacEvents 9}

    MacTimingAdvance ::= SEQUENCE {
        timerValue              INTEGER,
        timingAdvance           INTEGER
    }

-- This log is generated when BSR or scheduling request is triggered
bsrAndSrEvent OBJECT-TYPE
    SYNTAX  BsrAndSrEvent
    ACCESS  read-only
    STATUS  mandatory
    DESCRIPTION
    "BSR and SR Event"
::= {lteMacEvents 10}

    BsrAndSrEvent ::= SEQUENCE {
        causeMask           INTEGER
    }

        -------------------------------------------------------------------------------
        ------      mdmiLte MAC Messages                                   ------------
        -------------------------------------------------------------------------------

-- MAC Messages (transport block) from 3GPP 36.321
mac-OTA-Messages OBJECT-TYPE
    SYNTAX  MacMessageReport
    ACCESS  read-only
    STATUS  mandatory
    DESCRIPTION
    "MAC OTA Messages - most recent. Maximum"
::= {lteMacMessages 1}

    MacMessageReport ::= SEQUENCE OF MacMessage

    MacMessage ::= SEQUENCE {
        sysFrameNumber    SystemFrameNumber,
        subFrameNumber    SubFrameNumber,
        mac-version Version3gpp,
        direction   OtaMessageDirection,
        transportChannel TransportChannel,
        macHeader  OCTET STRING(SIZE (0..32))    -- Entire header and the control elements in raw bytes until the beginning of the first MAC SDU, max 32 bytes
    }
    TransportChannel ::= INTEGER {
        bch (1),
        dl-sch (2),
        pch (3),
        mch (4),
        ul-sch (5),
        rach (6)
    }

    -------------------------------------------------------------------------------
    ------      mdmiLte RLC                                            ------------
    -------------------------------------------------------------------------------

        -------------------------------------------------------------------------------
        ------      mdmiLte RLC Common Fields                              ------------
        -------------------------------------------------------------------------------

RadioBearerMode ::= INTEGER {
    AM (0),
    UM (1)   
}

SnFieldLength ::= INTEGER {
    size5 (1),
    size10 (2)
}

RlcPduStatus ::= INTEGER {
    PduData (0),
    PduCtrl (1),
    PduInvalid (2),
    PduDropped (3),
    UmPduDiscarded (4)
}

RlcThroughputObject ::= SEQUENCE {
    timeStamp       TimeStamp,
    location        LocationResult,
    throughput      INTEGER             --in kbps
}

        -------------------------------------------------------------------------------
        ------      mdmiLte RLC KPIs                                       ------------
        -------------------------------------------------------------------------------

rlcThroughputDL OBJECT-TYPE
-- Downlink throughput measured by the UE during an ftp-download session, on the RLC sub-layer
-- RLC from 3GPP TS 36.322
-- http://www.etsi.org/deliver/etsi_ts/136300_136399/136322/12.02.00_60/ts_136322v120200p.pdf
    SYNTAX  RlcThroughputObject
    ACCESS  read-only
    STATUS  mandatory
    DESCRIPTION
    "Downlink throughput measured by the UE on the RLC sub-layer. Object is time-stamped and geo-referenced."
::= {lteRlcKpis 1}

rlcThroughputUL OBJECT-TYPE
-- Uplink throughput measured by the UE during an ftp-download session, on the RLC sub-layer
-- RLC from 3GPP TS 36.322
-- http://www.etsi.org/deliver/etsi_ts/136300_136399/136322/12.02.00_60/ts_136322v120200p.pdf
    SYNTAX  RlcThroughputObject
    ACCESS  read-only
    STATUS  mandatory
    DESCRIPTION
    "Uplink throughput measured by the UE on the RLC sub-layer. Object is time-stamped and geo-referenced."
::= {lteRlcKpis 2}

-- This log is generated every 1s  
rlcDlStats OBJECT-TYPE
    SYNTAX  RlcDlStats
    ACCESS  read-only
    STATUS  mandatory
    DESCRIPTION
    "RLC DL statistics"
::= {lteRlcKpis 3}
    
    RlcDlStats ::= SEQUENCE {
        rlcDlRadioBearers                    SEQUENCE OF RlcDlRb         -- RlcDlStats consists a list of RlcDlRb for different radio bearers
    }     
    
    RlcDlRb ::= SEQUENCE {
        configurationIndex                   INTEGER(0..34),     -- Unique radio bearer configuration index
        mode                                 RadioBearerMode,    -- Logical Channel Mode
        reestablishmentCount                 INTEGER,            -- Total count of RLC reestablishment
        rxDataPduCount                       INTEGER,            -- Total count of RLC Data PDUs received
        rxDataPduBytes                       INTEGER,            -- Total count of RLC Data PDU received in bytes
        rxControlPduCount                    INTEGER,            -- Total count of RLC Control PDUs received
        rxControlPduBytes                    INTEGER,            -- Total count of RLC Control PDU received in bytes
        pduInvalidCount                      INTEGER,            -- Total count of RLC PDUs invalid
        pduInvalidBytes                      INTEGER,            -- Total count of RLC PDUs invalid in bytes   
        pduRetransmittedCount                INTEGER,            -- Total count of RLC PDUs retransmitted from receiver perspective
        pduRetransmittedBytes                INTEGER,            -- Total count of RLC PDUs retransmitted in bytes from receiver perspective
        pduDuplicateCount                    INTEGER,            -- Total count of RLC PDUs duplicated
        pduDuplicateBytes                    INTEGER,            -- Total count of RLC PDUs duplicated in bytes
        pduDroppedCount                      INTEGER,            -- Total count of PDUs dropped excluding duplicated
        pduDroppedBytes                      INTEGER,            -- Total count of PDUs dropped in bytes excluding duplicated
        txControlPduCount                    INTEGER,            -- Total count of control PDUs sent
        completeNackCount                    INTEGER,            -- Total count of complete RLC PDU NACKs sent
        segmentNackCount                     INTEGER,            -- Total count of RLC segments NACk sent
        missedUmPduCount                     INTEGER,            -- Total count of UM PDUs missing on DL
        sduOutOrder                          INTEGER,            -- Total count of out of order SDUs forwarded to PDCP during RLC reestablishment
        pduDroppedCountFlowControl           INTEGER,
        pduDroppedBytesFlowControl           INTEGER,
        sduReassembCount                     INTEGER,
        sduReassembBytes                     INTEGER,
        tReorderingExpiryCount               INTEGER,
        tReorderingStartCount                INTEGER,
        rxDataPduCountReEstb                 INTEGER,            -- Total count of RLC Data PDUs received since the last RLC re-establishment
        rxDataPduBytesReEstb                 INTEGER,            -- Total count of RLC Data PDU received in bytes since the last RLC re-establishment
        rxControlPduCountReEstb              INTEGER,            -- Total count of RLC Control PDUs received since the last RLC re-establishment
        rxControlPduBytesReEstb              INTEGER,            -- Total count of RLC Control PDU received in bytes since the last RLC re-establishment
        pduInvalidCountReEstb                INTEGER,            -- Total count of RLC PDUs invalid since the last RLC re-establishment
        pduInvalidBytesReEstb                INTEGER,            -- Total count of RLC PDUs invalid in bytes since the last RLC re-establishment
        pduRetransmittedCountReEstb          INTEGER,            -- Total count of RLC PDUs retransmitted from receiver perspective since the last RLC re-establishment
        pduRetransmittedBytesReEstb          INTEGER,            -- Total count of RLC PDUs retransmitted in bytes from receiver perspective since the last RLC re-establishment
        pduDuplicateCountReEstb              INTEGER,            -- Total count of RLC PDUs duplicated since the last RLC re-establishment
        pduDuplicateBytesReEstb              INTEGER,            -- Total count of RLC PDUs duplicated in bytes since the last RLC re-establishment
        pduDroppedCountReEstb                INTEGER,            -- Total count of PDUs dropped excluding duplicated since the last RLC re-establishment
        pduDroppedBytesReEstb                INTEGER,            -- Total count of PDUs dropped in bytes excluding duplicated since the last RLC re-establishment
        txControlPduCountReEstb              INTEGER,            -- Total count of control PDUs sent since the last RLC re-establishment
        completeNackCountReEstb              INTEGER,            -- Total count of complete RLC PDU NACKs sent since the last RLC re-establishment
        segmentNackCountReEstb               INTEGER,            -- Total count of RLC segments NACk sent since the last RLC re-establishment
        missedUmPduCountReEstb               INTEGER,            -- Total count of UM PDUs missing on DL since the last RLC re-establishment
        sduOutOrderReEstb                    INTEGER,            -- Total count of out of order SDUs forwarded to PDCP during RLC reestablishment since the last RLC re-establishment
        pduDroppedCountFlowControlReEstb     INTEGER,
        pduDroppedBytesFlowControlReEstb     INTEGER,
        sduReassembCountReEstb               INTEGER,
        sduReassembBytesReEstb               INTEGER,
        tReorderingExpiryCountReEstb         INTEGER,
        tReorderingStartCountReEstb          INTEGER
    }
    
-- This log is generated every 1s
rlcUlStats OBJECT-TYPE
    SYNTAX  RlcUlStats
    ACCESS  read-only
    STATUS  mandatory
    DESCRIPTION
    "RLC UL statistics"
::= {lteRlcKpis 4}
    
    RlcUlStats ::= SEQUENCE {
        rlcUlRadioBearers                    SEQUENCE OF RlcUlRb         -- RlcUlStats consists a list of RlcUlRb for different radio bearers
    }

    RlcUlRb ::= SEQUENCE {
        configurationIndex              INTEGER(0..34),     -- Unique radio bearer configuration index
        mode                            RadioBearerMode,    -- Logical Channel Mode
        numReestablishment              INTEGER,            -- Total count of RLC reestablishment
        txDataPduCount                  INTEGER,            -- Total count of New Data PDU transmitted
        txDataPduBytes                  INTEGER,            -- Total count of New Data PDU transmitted in bytes including RLC headers
        txSduCount                      INTEGER,            -- Total count of RLC SDUs transmitted
        txSduBytes                      INTEGER,            -- Total count of RLC SDU in bytes transmitted
        txControlPduCount               INTEGER,            -- Total count of RLC control PDU transmitted
        txControlPduBytes               INTEGER,            -- Total count of RLC Control PDU transmitted in bytes
        pduRetransmittedCount           INTEGER,            -- Total count of RLC PDUs retransmitted
        pduRetransmittedBytes           INTEGER,            -- Total count of RLC PDUs retransmitted in bytes
        rxControlPduCount               INTEGER,            -- Total count of RLC Control PDUs received            
        completeNackCount               INTEGER,            -- Total count of Complete RLC PDU NACKs received
        segmentNackCount                INTEGER,            -- Total count of NACKs for RLC Segments received
        rxInvalidControlPduCount        INTEGER,            -- Total count of invalid control PDU received
        numPoll                         INTEGER,
        numTPollRetransmitExpiry        INTEGER,
        txDataPduCountReEstb            INTEGER,            -- Total count of New Data PDU transmitted since last RLC re-establishemnet
        txDataPduBytesReEstb            INTEGER,            -- Total count of New Data PDU transmitted in bytes including RLC headers since last RLC re-establishemnet
        txSduCountReEstb                INTEGER,            -- Total count of RLC SDUs transmitted since last RLC re-establishemnet
        txSduBytesReEstb                INTEGER,            -- Total count of RLC SDU in bytes transmitted since last RLC re-establishemnet
        txControlPduCountReEstb         INTEGER,            -- Total count of RLC control PDU transmitted since last RLC re-establishemnet
        txControlPduBytesReEstb         INTEGER,            -- Total count of RLC Control PDU transmitted in bytes since last RLC re-establishemnet
        pduRetransmittedCountReEstb     INTEGER,            -- Total count of RLC PDUs retransmitted since last RLC re-establishemnet
        pduRetransmittedBytesReEstb     INTEGER,            -- Total count of RLC PDUs retransmitted in bytes since last RLC re-establishemnet
        rxControlPduCountReEstb         INTEGER,            -- Total count of RLC Control PDUs received since last RLC re-establishemnet
        completeNackCountReEstb         INTEGER,            -- Total count of Complete RLC PDU NACKs received since last RLC re-establishemnet
        segmentNackCountReEstb          INTEGER,            -- Total count of NACKs for RLC Segments received since last RLC re-establishemnet
        rxInvalidControlPduCountReEstb  INTEGER,            -- Total count of invalid control PDU received since last RLC re-establishemnet
        numPollReEstb                   INTEGER,
        numTPollRetransmitExpiryReEstb  INTEGER
    }

-- This log is generated every 50ms
rlcUlUmDataPdu OBJECT-TYPE
    SYNTAX  RlcUlUmDataPdu
    ACCESS  read-only
    STATUS  mandatory
    DESCRIPTION
    "RLC UL UM Data PDU"
::= {lteRlcKpis 5}
    
    RlcUlUmDataPdu ::= SEQUENCE {
        rbConfigIndex       INTEGER (0..34),
        rbMode              RadioBearerMode,
        snFieldLen          SnFieldLength,
        logMask             INTEGER (0..65535),      -- description as below
        pduLogged           RlcPduLogged     
    }

    -- logMask, Bit 0 is the Least Significant Bit
    -- Bit 0, reserved
    -- Bit 1, RLCUL config log
    -- Bit 2, RLCUL AM all PDU log
    -- Bit 3, RLCUL control PDU log
    -- Bit 4, RLCUL polling log
    -- Bit 5, RLCUL signaling log
    -- Bit 6, RLCUL UM data PDU log
    -- Bit 7, RLCUL statistics log
    -- Bit 8, RLCUL AM state log
    -- Bit 9, RLCUL UM state log
    -- Bit 10 to Bit 15, reserved
    
    RlcPduLogged ::= SEQUENCE {
        pduSize                 INTEGER (0..65535),     -- PDU size
        numBytesLogged          INTEGER (0..65535),     -- number of bytes logged
        status                  RlcPduStatus,
        extensionBit            BOOLEAN,
        lengthIndicator         INTEGER,
        framingInfo             INTEGER                 -- 3GPP TS 36.322 Table 6.2.2.6-1           
    }

-- This log is generated every 50ms
rlcDlUmDataPdu OBJECT-TYPE
    SYNTAX  RlcDlUmDataPdu
    ACCESS  read-only
    STATUS  mandatory
    DESCRIPTION
    "RLC DL UM Data PDU"
::= {lteRlcKpis 6}
    
    RlcDlUmDataPdu ::= SEQUENCE {
        rbConfigIndex       INTEGER (0..34),
        rbMode              RadioBearerMode,
        snFieldLen          SnFieldLength,
        logMask             INTEGER (0..65535),      -- description as below
        pduLogged           RlcPduLogged     
    }

    -- logMask, Bit 0 is the Least Significant Bit
    -- Bit 0, reserved
    -- Bit 1, RLCDL config log
    -- Bit 2, RLCDL AM all PDU log
    -- Bit 3, RLCDL control PDU log
    -- Bit 4, RLCDL polling log
    -- Bit 5, RLCDL signaling log
    -- Bit 6, RLCDL UM data PDU log
    -- Bit 7, RLCDL statistics log
    -- Bit 8, RLCDL AM state log
    -- Bit 9, RLCDL UM state log
    -- Bit 10 to Bit 15, reserved

        -------------------------------------------------------------------------------
        ------      mdmiLte RLC Events                                     ------------
        -------------------------------------------------------------------------------
        -------------------------------------------------------------------------------
        ------      mdmiLte RLC Messages                                   ------------
        -------------------------------------------------------------------------------

-- RLC Messages from 3GPP 36.322
rlc-OTA-Messages OBJECT-TYPE
    SYNTAX  RlcMessageReport
    ACCESS  read-only
    STATUS  mandatory
    DESCRIPTION
    "RLC OTA Messages - most recent."
::= {lteRlcMessages 1}

    RlcMessageReport ::= SEQUENCE OF RlcMessage

    RlcMessage ::= SEQUENCE {
        rlc-version         Version3gpp,
        direction           OtaMessageDirection,
        type                RlcMessageType,
        rlcMode             RlcMode,
        snFieldLength       SnFieldLength,
        lIField             BOOLEAN,
        rlcHeader           OCTET STRING(SIZE (0..16))    -- Entire RLC header in raw bytes, max 16 bytes
    }
    RlcMessageType ::= INTEGER {
        data (1),
        control (2)
    }


    -------------------------------------------------------------------------------
    ------      mdmiLte PDCP                                           ------------
    -------------------------------------------------------------------------------

        -------------------------------------------------------------------------------
        ------      mdmiLte PDCP Common Fields                              ------------
        -------------------------------------------------------------------------------
PdcpThroughputObject ::= SEQUENCE {
    timeStamp       TimeStamp,
    location        LocationResult,
    throughput      INTEGER             --in kbps
}
        -------------------------------------------------------------------------------
        ------      mdmiLte PDCP KPIs                                      ------------
        -------------------------------------------------------------------------------

pdcpThroughputDL OBJECT-TYPE
-- Downlink throughput measured by the UE during an ftp-download session, on the PDCP sub-layer
-- PDCP from 3GPP TS 36.323
-- http://www.etsi.org/deliver/etsi_ts/136300_136399/136323/12.03.00_60/ts_136323v120300p.pdf
    SYNTAX  PdcpThroughputObject
    ACCESS  read-only
    STATUS  mandatory
    DESCRIPTION
    "Downlink throughput measured by the UE on the PDCP sub-layer. Object is time-stamped and geo-referenced."
::= {ltePdcpKpis 1}

pdcpThroughputUL OBJECT-TYPE
-- Uplink throughput measured by the UE during an ftp-download session, on the PDCP sub-layer
-- PDCP from 3GPP TS 36.323
-- http://www.etsi.org/deliver/etsi_ts/136300_136399/136323/12.03.00_60/ts_136323v120300p.pdf
    SYNTAX  PdcpThroughputObject
    ACCESS  read-only
    STATUS  mandatory
    DESCRIPTION
    "Uplink throughput measured by the UE on the PDCP sub-layer. Object is time-stamped and geo-referenced."
::= {ltePdcpKpis 2}

-- This log is generated every 1s
pdcpDlStats OBJECT-TYPE
    SYNTAX  PdcpDlStats
    ACCESS  read-only
    STATUS  mandatory
    DESCRIPTION
    "PDCP DL statistics"
::= {ltePdcpKpis 3}

    PdcpDlStats ::= SEQUENCE OF PdcpDlRb        -- PdcpDlStats consists a list of PdcpDlRb for different radio bearers
    
    PdcpDlRb ::= SEQUENCE {
        configurationIndex                      INTEGER(0..34),     -- Unique radio bearer configuration index
        rxDataPduBytes                          INTEGER,            -- Total number of PDCP Data PDU received in bytes
        rxControlPduBytes                       INTEGER,            -- Total number of PDCP Control PDU received in bytes
        rohcFailNum                             INTEGER,            -- Total number of PDCP PDUs ROHC decompression failed
        integrityFailNum                        INTEGER,            -- Total number of PDCP PDUs integrity check failed
        missSduToUl                             INTEGER,            -- Total number of PDCP SDUs missing when delivered to upper layers
        missSduFromLl                           INTEGER,            -- Total number of PDCP SDUs missing from RLC since reestablishment
        pduDuplicateBytes                       INTEGER,            -- Total number of PDCP PDUs duplicated in bytes
        pduInvalidBytes                         INTEGER,            -- Total number of PDCP PDUs invalid in bytes
        numReestablishments                     INTEGER,
        numDataPduBytesReceived                 INTEGER,
        numControlPdusReceived                  INTEGER,
        numStatusReportPdusReceived             INTEGER,
        numDuplicatedPdus                       INTEGER,
        numPdusOutOfReorderingWindow            INTEGER,
        numPduBytesOutOfReorderingWindow        INTEGER,
        numInvalidPdus                          INTEGER,
        numDataPduBytesReceivedSinceLastReestablishment         INTEGER,
        numControlPdusReceivedSinceLastReestablishment          INTEGER,
        numControlPduBytesReceivedSinceLastReestablishment      INTEGER,
        numStatusReportPdusReceivedSinceLastReestablishment     INTEGER,
        numRohcPdusDecompressionFailureSinceLastReestablishment INTEGER,
        numPduIntegrityVerificationFailureSinceLastReestablishmen INTEGER,
        numMissingSdusAfterDeliveryToUpperLayerSinceLastReestablishment INTEGER,
        numMissingSdusFromRlcSinceLastReestablishment           INTEGER,
        numDuplicatedPdusSinceLastReestablishment               INTEGER,
        numDuplicatedPduBytesSinceLastReestablishment           INTEGER,
        numPdusOutOfReorderingWindowSinceLastReestablishment    INTEGER,
        numOfPduBytesOutOfReorderingWindowSinceLastReestablishment  INTEGER,
        numOfInvalidPdusSinceLastReestablishment            INTEGER,
        numOfInvalidPduBytesSinceLastReestablishment        INTEGER
    }
    
    
-- This log is generated every 1s 
pdcpUlStats OBJECT-TYPE
    SYNTAX  PdcpUlStats
    ACCESS  read-only
    STATUS  mandatory
    DESCRIPTION
    "PDCP UL statistics"
::= {ltePdcpKpis 4}

    PdcpUlStats ::= SEQUENCE OF PdcpUlRb            -- PdcpUlStats consists a list of PdcpUlRb for different radio bearers
    
    PdcpUlRb ::= SEQUENCE {
        configurationIndex      INTEGER(0..34),     -- Unique radio bearer configuration index
        txDataPduBytes          INTEGER,            -- Total number of PDCP Data PDU transmitted in bytes
        txControlPduBytes       INTEGER,            -- Total number of PDCP Control PDU transmitted in bytes
        pduRohcFail             INTEGER,            -- Total number of PDCP PDUs ROHC compression failed
        sduDiscardBytes         INTEGER,            -- Total number of PDCP SDUs discarded in bytes
        pduRetransmittedBytes   INTEGER,            -- Total number of PDCP PDUs retransmitted in bytes
        numReestablishments                     INTEGER,
        numControlPdusSent                      INTEGER,
        numStatusReportPdusSent                 INTEGER,
        numSdusDiscardedByDiscardTimer          INTEGER,
        numPdusRetransmittedDuringHo            INTEGER,
        numSdusDiscardedByDiscardTimerSinceLastReestablishment INTEGER,
        numSduBytesDiscardedByDiscardTimerSinceLastReestablishment INTEGER,
        numDataPduBytesSentSinceLastReestablishment INTEGER,
        numControlPdusSentSinceLastReestablishment INTEGER,
        numControlPduBytesSentSinceLastReestablishment INTEGER,
        numStatusReportPdusSentSinceLastReestablishment INTEGER,
        numRohcPdusDecompressionFailureSinceLastReestablishmen INTEGER
    }

        -------------------------------------------------------------------------------
        ------      mdmiLte PDCP Events                                    ------------
        -------------------------------------------------------------------------------
        -------------------------------------------------------------------------------
        ------      mdmiLte PDCP Messages                                  ------------
        -------------------------------------------------------------------------------

-- This log is generated either when 20 records have been collected, or when 500ms have passed from previous log timestamp, whichever happens first.
-- PDCP Messages from 3GPP 36.323
pdcp-OTA-Message OBJECT-TYPE
    SYNTAX  PdcpMessageReport
    ACCESS  read-only
    STATUS  mandatory
    DESCRIPTION
    "PDCP OTA Message - most recent."
::= {ltePdcpMessages 1}

    PdcpMessageReport ::= SEQUENCE OF PdcpMessageRecord
    PdcpMessageRecord ::= SEQUENCE {
        pdcp-version            Version3gpp,
        direction               OtaMessageDirection,
        type                    PdcpMessageType,
        radioBearerType         RadioBearerType,
        rlcMode                 RlcMode,
        pdcpSnSize              PdcpSnSize,
        radioBearerConfigId     INTEGER,
        pdcpHeader              OCTET STRING(SIZE (0..8))    -- Entire PDCP header in raw bytes, max 8 bytes
    }
    PdcpMessageType ::= INTEGER {
        data (1),
        control (2)
    }
    RadioBearerType ::= INTEGER {
        drb (1),
        srb (2)
    }
    RlcMode ::= INTEGER {
        rlc-am (1),
        rlc-um (2)
    }
    PdcpSnSize ::= INTEGER {
        null (0),
        len7bits (1),
        len12bits (2),
        len15bits (3)
    }

    -------------------------------------------------------------------------------
    ------      mdmiLte Physical Layer                                 ------------
    -------------------------------------------------------------------------------

        -------------------------------------------------------------------------------
        ------      mdmiLte Phy Common Fields                              ------------
        -------------------------------------------------------------------------------

TransmissionMode ::= INTEGER {
    tmInvalid (0),
    tmSingleAntPort0 (1),
    tmTdRank1 (2),
    tmOlSm (3),
    tmClSm (4),
    tmMuMimo (5),
    tmClRank1Pc (6),
    tmSingleAntPort5 (7),
    mode8 (8),
    mode9 (9)
}

CrcResult ::= INTEGER {
    Fail (0),
    Pass (1)
}

CecAggregationLevel ::= INTEGER {
    agg1 (0),
    agg2 (1),
    agg4 (2),
    agg8 (3)
}

SearchSpaceType ::= INTEGER {
    Common (0),
    User (1)
}

HarqCombining ::= INTEGER {
    Disabled (0),
    Enabled (1)
}

        -------------------------------------------------------------------------------
        ------      mdmiLte Physical Layer Debug                           ------------
        -------------------------------------------------------------------------------
-- This log shall be reported when 20 records/measurements have been collected, or when 500ms have passed from the previous OID log timestamp, whichever happens first. Each record/measurement shall be reported as and when a change occurs
lteCellTiming OBJECT-TYPE
    SYNTAX  LteCellTiming
    ACCESS  read-only
    STATUS  mandatory
    DESCRIPTION
    "Provide informations about cell timing"
::= {ltePhyDebug 1} 

    LteCellTiming ::= SEQUENCE {
        startingSysFrameNum         SystemFrameNumber,
        startingSubFrameNum         SubFrameNumber,
        startingDlFrameTimingOffset INTEGER(0..307200), -- Downlink timing advance divided by 2. In Ts units
        startingUlFrameTimingOffset INTEGER(0..307200), -- Starting NTA value (in units of 16 Ts). NTA= timing offset between uplink and downlink radio frames at the UE, expressed in units of Ts
        startingUlTimingAdvance     INTEGER(0..307200), -- The first value of UL timing advance in Ts units
        timingAdjusts               SEQUENCE OF TimingAdjust
    }

    TimingAdjust ::= SEQUENCE {
        dlFrameTimingChange     INTEGER(-512..511),     -- dlFrameTimingChange = DlFrameTimingOffset for subframe #n - DlFrameTimingOffset for subframe #n+1. startingDlFrameTimingOffset=the first value of DL frame timing offset 
        ulFrameTimingChange     INTEGER(-1024..1023),   -- ulFrameTimingChange = ulFrameTimingOffset for subframe #n - ulFrameTimingOffset for subframe #n+1. This parameter should include timing advance corresponding to TA command.
        timingAdvanceChange     INTEGER(-128..127)      -- change in the value of TA
    }

        -------------------------------------------------------------------------------
        ------      mdmiLte Physical Layer Measurements                    ------------
        -------------------------------------------------------------------------------

-- This log shall be reported when 20 records/measurements have been collected, or when 500ms have passed from the previous OID log timestamp, whichever happens first. Each record/measurement shall be reported as and when a change occurs
servingCellMeasurement OBJECT-TYPE
    SYNTAX  ServingCellMeasurements
    ACCESS  read-only
    STATUS  mandatory
    DESCRIPTION
    "Measurements of Serving Cell"
::= {ltePhyMeasurements 1}

    ServingCellMeasurements ::= SEQUENCE OF ServingCellMeasurement

    ServingCellMeasurement ::= SEQUENCE {
        sysFrameNumber      SystemFrameNumber,
        subFrameNumber      SubFrameNumber,
        pci                 INTEGER (0..504),
        rsrp                INTEGER (-180..-30),    -- RSRP Value in dBm    
        rsrp0               INTEGER (-180..-30),    -- RSRP Value for Rx0 in dBm
        rsrp1               INTEGER (-180..-30),    -- RSRP Value for Rx1 in dBm
        rsrq                INTEGER (-30..10),      -- RSRQ Value in dB
        rsrq0               INTEGER (-30..10),      -- RSRQ Value for Rx0 in dB
        rsrq1               INTEGER (-30..10),      -- RSRQ Value for Rx1 in dB
        rssi                INTEGER (-110..-10),    -- RSSI Value in dBm. For standalone RSSI use RSSI0 and for combined RSSI use the average of RSSI0 and RSSI1
        rssi0               INTEGER (-110..-10),    -- RSSI Value for Rx0 in dBm
        rssi1               INTEGER (-110..-10),    -- RSSI Value for Rx1 in dBm
        sinr                INTEGER (-20..40),      -- SINR Value in dBm
        sinr0               INTEGER (-20..40),      -- SINR Value for Rx0 in dBm
        sinr1               INTEGER (-20..40),      -- SINR Value for Rx1 in dBm
        earfcn              Earfcn,                 -- EARFCN
        priority            INTEGER (0..7),         -- The priority of the layer that the cell resides on
        isIdleMode          BOOLEAN,
        bandWidth           Bandwidth,
        carrierType         CarrierType               
    }

-- This log shall be reported when 20 records/measurements have been collected, or when 500ms have passed from the previous OID log timestamp, whichever happens first. Each record/measurement shall be reported as and when a change occurs
neighborCellMeasurements OBJECT-TYPE
    SYNTAX  NeighborCellMeasurementReport
    ACCESS  read-only
    STATUS  mandatory
    DESCRIPTION
    "Neighbor Cell Measurements"
::= {ltePhyMeasurements 2}

    NeighborCellMeasurementReport ::= SEQUENCE OF NeighborCellMeasurements

    -- Each "NeighborCellMeasurements" record can contain measurements of up to 20 unique detected neighbor cells. Each record should include all currently detected neighbor cells and should be reported at each measurement occasion or whenever a change in one of the detected neighbor cells is identified.
    NeighborCellMeasurements ::= SEQUENCE OF NeighborCellMeasurement        -- up to 20 detected neighbor cells
    NeighborCellMeasurement ::= SEQUENCE {
        sysFrameNumber      SystemFrameNumber,
        subFrameNumber      SubFrameNumber,
        pci                 INTEGER (0..504),
        rsrp                INTEGER (-180..-30),    -- RSRP Value in dBm    
        rsrp0               INTEGER (-180..-30),    -- RSRP Value for Rx0 in dBm
        rsrp1               INTEGER (-180..-30),    -- RSRP Value for Rx1 in dBm
        rsrq                INTEGER (-30..10),      -- RSRQ Value in dB
        rsrq0               INTEGER (-30..10),      -- RSRQ Value for Rx0 in dB
        rsrq1               INTEGER (-30..10),      -- RSRQ Value for Rx1 in dB
        rssi                INTEGER (-110..-10),    -- RSSI Value in dBm
        rssi0               INTEGER (-110..-10),    -- RSSI Value for Rx0 in dBm
        rssi1               INTEGER (-110..-10),    -- RSSI Value for Rx1 in dBm
        earfcn              Earfcn,                 -- EARFCN
        priority            INTEGER (0..7),         -- The priority of the layer that the cell resides on
        duplexType          DuplexType
    }

dlPhysLayerThroughputValue OBJECT-TYPE
    SYNTAX  Throughput
    ACCESS  read-only
    STATUS  mandatory
    DESCRIPTION
    "L1 downlink throughput measured at the HARQ level. Transport blocks received by the UE with CRC errors shall be included."
::= {ltePhyMeasurements 5}

    Throughput ::= SEQUENCE {
        sysFrameNumber      SystemFrameNumber,
        subFrameNumber      SubFrameNumber,
        throughput          INTEGER 
    }

ulPhysLayerThroughputValue OBJECT-TYPE
    SYNTAX  Throughput
    ACCESS  read-only
    STATUS  mandatory
    DESCRIPTION
    "L1 uplink throughput measured at the HARQ level, excluding the transport blocks received by the UE with CRC errors."
::= {ltePhyMeasurements 6}

-- This event is generated when the timing advance control element is received
timingAdvanceEvent OBJECT-TYPE
    SYNTAX  TimingAdvance
    ACCESS  read-only
    STATUS  mandatory
    DESCRIPTION
    "Timing Advance Event"
::= {ltePhyMeasurements 7}

    TimingAdvance ::= SEQUENCE {
        sysFrameNumber      SystemFrameNumber,
        subFrameNumber      SubFrameNumber,
        timingAdvance       INTEGER             --in TA units microseconds 
    }

-- This event is generated every time a PHR is triggered
txPowerHeadroomEvent OBJECT-TYPE
    SYNTAX  Headroom
    ACCESS  read-only
    STATUS  mandatory
    DESCRIPTION
    "Total remaining power at the UE before reaching its maximum nominal power."
::= {ltePhyMeasurements 8}

    Headroom ::= SEQUENCE {
        sysFrameNumber      SystemFrameNumber,
        subFrameNumber      SubFrameNumber,
        headroom-value      INTEGER (-23..40)  --headroom value in dB
    }

-- This log shall be reported when 20 records/measurements have been collected, or when 500ms have passed from the previous OID log timestamp, whichever happens first. Each record/measurement shall be reported as and when a change occurs
-- PSS is only for the serving cell (Pcell) the device is trying to camp on. Not the neighbor cells.
pssResult OBJECT-TYPE
    SYNTAX  PssResult
    ACCESS  read-only
    STATUS  mandatory
    DESCRIPTION
    "parameters related to PSS"
::= {ltePhyMeasurements 10}
    
    PssResult ::= SEQUENCE OF PssRecord

    PssRecord ::= SEQUENCE {
        sysFrameNumber      SystemFrameNumber,
        subFrameNumber      SubFrameNumber,
        peakValue           INTEGER,             -- PSS peak value in dB
        peakPosition        INTEGER (0..10000),  -- Sample position with 5ms resolution
        index               INTEGER (0..2)       -- PSS index
    }
       
-- This log shall be reported when 20 records/measurements have been collected, or when 500ms have passed from the previous OID log timestamp, whichever happens first. Each record/measurement shall be reported as and when a change occurs
-- SSSResult should be for serving cell (Pcell, not Scell) and all the detected and barred cells (neighbor cells)
sssResult OBJECT-TYPE
    SYNTAX  SssResult
    ACCESS  read-only
    STATUS  mandatory
    DESCRIPTION
    "parameters related to SSS"
::= {ltePhyMeasurements 11}

    SssResult ::= SEQUENCE OF SssCellInfo
    SssCellInfo ::= SEQUENCE {
        sysFrameNumber      SystemFrameNumber,
        subFrameNumber      SubFrameNumber,
        pci                 INTEGER (0..504),
        peakValue           INTEGER,                -- SSS peak value in dB
        frameBoundary       INTEGER,                -- Frame boundary RTC counter
        cyclicPrefix        CyclicPrefix,            -- Cyclic prefix used
        barredCells         SEQUENCE OF BarredCell,
        detectedCells       SEQUENCE OF DetectedCell
    }
    
    CyclicPrefix ::= INTEGER {                  -- Cyclic prefix used
        normal (0),
        extended (1)
    }

    BarredCell ::= SEQUENCE {
        cellId  INTEGER (0..504)
    }

    DetectedCell ::= SEQUENCE {
        cellId  INTEGER (0..504),
        earfcn  Earfcn
    }
 
-- This log is generated when there is a RACH attempt
rachMsgReport OBJECT-TYPE
    SYNTAX  RachMsgReport
    ACCESS  read-only
    STATUS  mandatory
    DESCRIPTION
    "RACH MSG 1 2 3 4 info"
::= {ltePhyMeasurements 12}

    RachMsgReport ::= SEQUENCE {
        sysFrameNumber      SystemFrameNumber,
        subFrameNumber      SubFrameNumber,
        msg1    CHOICE {
            msg1Null        NULL,               -- unavailable
            msg1Content     Msg1Content
        },
        msg2    CHOICE {
            msg2Null        NULL,               -- unavailable
            msg2Content     Msg2Content
        },
        msg3    CHOICE {
            msg3Null        NULL,               -- unavailable
            msg3Content     Msg3Content
        },
        msg4    CHOICE {
            msg4Null        NULL,               -- unavailable
            msg4Content     Msg4Content
        }
    }
    
    Msg1Content ::= SEQUENCE {
        sequence        INTEGER (0..63),        -- Preamble sequence index
        prachTxPower    INTEGER (-112..23),     -- PRACH tx power
        duplexMode      INTEGER (0..1)          -- 0: FDD   1: TDD
    }
    
    Msg2Content ::= SEQUENCE {
        timingAdvance           CHOICE {
            timingAdvanceNull   NULL,
            timingAdvanceValue  INTEGER             -- in TA units microseconds
        },
        contentionType          INTEGER (0..1),     -- 0: Contention Free   1: Contention Based
        rntiType                RntiType,           -- RNTI type
        rntiValue               INTEGER             -- RNTI Value
    }
    
    RntiType ::= INTEGER {
        cRnti (0),              -- C-RNTI
        spsRnti (1),            -- SPS-RNTI
        pRnti (2),              -- P-RNTI
        raRnti (3),             -- RA-RNTI
        tempCRnti (4),          -- TEMP-C-RNTI
        siRnti (5),             -- SI-RNTI
        tpcPuschRnti (6),       -- TPC-PUSCH-RNTI
        tpcPucchRnti (7),       -- TPC-PUCCH-RNTI
        mbmsRnti (8)            -- MBMS-RNTI
    }
    
    Msg3Content ::= SEQUENCE {
        mcs                 INTEGER,            -- Modulation and Coding Scheme
        modulationType      ModulationType,   -- Modulation stream type
        startRb             INTEGER (1..110),   -- Starting resource block number of the received grant
        numRb               INTEGER (1..110),   -- Total number of Resource blocks allocated in the grant
        tbSizeIndex         INTEGER (0..26)     -- Transport block size index
    }

    ModulationType ::= INTEGER {
        BPSK (0),
        QPSK (1),
        QAM16 (2),
        QAM64 (3)
    }
    
    Msg4Content ::= SEQUENCE {
        contentionResult    INTEGER {           -- Contention result
            failed (0),
            passed (1)
        }
    }

mimoPDSCHthroughput0Value OBJECT-TYPE
    SYNTAX  Throughput
    ACCESS  read-only
    STATUS  mandatory
    DESCRIPTION
    "PDSCH data rate measured by the UE for the downlink on the code word 0 layer."
::= {ltePhyMeasurements 13}

mimoPDSCHthroughput1Value OBJECT-TYPE
    SYNTAX  Throughput
    ACCESS  read-only
    STATUS  mandatory
    DESCRIPTION
    "PDSCH data rate measured by the UE for the downlink on the code word 1 layer."
::= {ltePhyMeasurements 14}

-- This log shall be reported when 20 records/measurements have been collected, or when 500ms have passed from the previous OID log timestamp, whichever happens first. Each record/measurement shall be reported as and when a change occurs
srsTxPowerMeasurement OBJECT-TYPE
    SYNTAX  SrsTxPowerReports
    ACCESS  read-only
    STATUS  mandatory
    DESCRIPTION
    "SRS Tx Power measurement"
::= {ltePhyMeasurements 15}
    
    SrsTxPowerReports ::= SEQUENCE OF SrsTxPowerReport

    SrsTxPowerReport ::= SEQUENCE {
        systemFrameNumber   SystemFrameNumber,
        subFrameNumber      SubFrameNumber,
        srsTxPowerValue     SrsTxPowerValue,
        fi                  PowerControlAccumalationFactor,     -- Power control accumalation factor
        pathLoss            INTEGER (0..255),
        srsTxBw             INTEGER (0..255)                    -- SRS Transmission Bandwidth
    }

    SrsTxPowerValue ::= INTEGER (-112..23)  --SRS Tx Power measurement in dB

-- This log shall be reported when 20 records/measurements have been collected, or when 500ms have passed from the previous OID log timestamp, whichever happens first. Each record/measurement shall be reported as and when a change occurs
srsTxReports OBJECT-TYPE
    SYNTAX  SrsTxReports
    ACCESS  read-only
    STATUS  mandatory
    DESCRIPTION
    "SRS Tx Report"
::= {ltePhyMeasurements 16}

    SrsTxReports ::= SEQUENCE {
        servingCellId        INTEGER (0..504),
        reports              SEQUENCE OF SrsTxReport
    }

    SrsTxReport ::= SEQUENCE {
        systemFrameNumber    SystemFrameNumber,
        subFrameNumber       SubFrameNumber,
        ueSrsEnabled         BOOLEAN,
        cellSrsEnabled       BOOLEAN,
        startRB              INTEGER (0..110),
        numOfRB              INTEGER (0..110),
        zcRoot               INTEGER (1..1151),
        carrierIndex         CarrierIndex,
        srsTxPower           INTEGER (-50..23),
        duplexType           DuplexType,
        upPtsType            UpPtsType,           
        srsTriggerType       SrsTriggerType,
        cyclicShift          CyclicShift,
        srsPowerOffset       SrsPowerOffset
    }

    UpPtsType ::= INTEGER {
        NoSrsPresent (0),
        SrsSentOnUpPtsSymbol0 (1),
        SrsSentOnUpPtsSymbol1 (2),
        SrsSentOnBothUpPtsSymbols (3)
    }

    SrsTriggerType ::= INTEGER {
        Type0 (0),
        Type1Dci0 (1),
        Type1Dci1A2B2C (2),
        Type1Dci4 (3)
    }

    CyclicShift ::= INTEGER (0..7)

    SrsPowerOffset ::= INTEGER {
        Offset0 (0),
        Offset1 (1)
    }

-- This log shall be reported when 20 records/measurements have been collected, or when 500ms have passed from the previous OID log timestamp, whichever happens first. Each record/measurement shall be reported as and when a change occurs
dciInformationReports OBJECT-TYPE
    SYNTAX  DciInformationReports
    ACCESS  read-only
    STATUS  mandatory
    DESCRIPTION
    "DCI Information Reports"
::= {ltePhyMeasurements 17}

    DciInformationReports ::= SEQUENCE {
        duplexType          DuplexType,
        reports             SEQUENCE OF DciInformationReport
    }
    
    DciInformationReport ::= SEQUENCE {
        systemFrameNumber   SystemFrameNumber,
        subFrameNumber      SubFrameNumber,
        pdcchOrderPresent   BOOLEAN,
        ulDciGrantInfo      CHOICE {
            ulDciGrantNotPresent    NULL,
            ulDciGrantPresent       UlDciGrantInfo
        },
        tpcDciInfo        CHOICE {
            tpcDciNotPresent      NULL,
            tpcDciPresent         UlTpcDciInfo
        },
        dlDciGrantInfo      SEQUENCE OF DlDciGrantInfo     -- If no DCI Grant Info presents, this SEQUENCE length can be zero
    }

    UlDciGrantInfo ::= SEQUENCE {
        mcsIndex                            INTEGER (0..31),
        cqiRequest                          INTEGER (0..3),
        startResourceBlock                  INTEGER (1..110),       -- starting RB for the received grant
        numResourceBlock                    INTEGER (1..110),       -- total number of TBs allocated in the grant
        tbSizeIndex                         INTEGER (0..31),        -- transport block size index
        modulationType                      ModulationType,
        hoppingFlag                         HoppingFlag,
        ndi                                 INTEGER,                -- New Data Indicator
        tpc                                 INTEGER,
        demodulationRefSignalCyclicShift    INTEGER,
        dci0KPusch                          INTEGER,
        redundancyVersionIndex              INTEGER
    }

    UlTpcDciInfo ::= SEQUENCE {
        tpcDciFormatType    TpcDciFormat   
    }

    DlDciGrantInfo ::= SEQUENCE {
        servingCellIndex    ServingCellIndex,
        dlGrantFormatType   DlGrantPdcchFormatType,
        numAckNacBits       INTEGER (0..2),
        dlGrantTpcCommand   INTEGER
    }

    DlTpcDciInfo ::= SEQUENCE {
        tpcDciRntiType      RntiType  
    }

    TpcDciFormat ::= INTEGER {
        Format3 (0),
        Format3a (1)
    }

    DlGrantPdcchFormatType ::= INTEGER {
        Format0 (0),
        Format1 (1),
        Format1a (2),
        Format1b (3),
        Format1c (4),
        Format1d (5),
        Format2 (6),
        Format2a (7)
    }

    HoppingFlag ::= INTEGER {
        Disabled (0),
        Enabled (1)
    }

ulGrantMcsIndex OBJECT-TYPE
    SYNTAX  MCS
    ACCESS  read-only
    STATUS  mandatory
    DESCRIPTION
    "UL Grant　MCS index"
::= {ltePhyMeasurements 18}

-- This log is generated every 500ms
radioLinkMonitoring OBJECT-TYPE
    SYNTAX  RadioLinkMonitoring
    ACCESS  read-only
    STATUS  mandatory
    DESCRIPTION
    "Radio Link Monitoring"
::= {ltePhyMeasurements 19}

    RadioLinkMonitoring ::= SEQUENCE OF RadioLinkMonitoringRecord

    RadioLinkMonitoringRecord ::= SEQUENCE {
        sysFrameNumber          SystemFrameNumber,
        subFrameNumber          SubFrameNumber,
        outOfSyncCount          INTEGER,
        inSyncCount             INTEGER,
        t310Timer               T310Timer
    }

    T310Timer ::= INTEGER {
        Stopped(0),
        Running(1)
    }


-- This log is generated every time RRC configures it or SIB2 get updated by the network.
pagingDRXEvent OBJECT-TYPE
    SYNTAX  PagingDRX
    ACCESS  read-only
    STATUS  mandatory
    DESCRIPTION
    "Paging DRX Event"
::= {ltePhyEvents 1}

    PagingDRX ::= SEQUENCE {
        earfcn                  Earfcn,
        pci                     INTEGER(0..504),
        pagingCycle             PagingCycle,
        nb                      DrxNb,
        ueId                    INTEGER (0..1023),      -- IMSI mod 1024
        drxSysFrameNumOffset    INTEGER,                -- drxSysFrameNumOffset is used to obtain the starting system frame number for DRX cycle.
        drxSubFrameNumOffset    INTEGER                 -- drxSubFrameNumOffset is used to obtain the starting sub frame number for DRX cycle.
    }

    PagingCycle ::= INTEGER {
        PagingCycle320ms (0),
        PagingCycle640ms (1),
        PagingCycle1280ms (2),
        PagingCycle2560ms (3)
    }

    DrxNb ::= INTEGER {
        FourT (0),
        TwoT (1),
        OneT (2),
        halfT (3),
        quarterT (4),
        oneEightT (5),
        oneSixteenthT (6),
        oneThirtySecondT (7)
    }

-- This log is generated every time a transmit power back off is set
txPowerBackOffEvent OBJECT-TYPE
    SYNTAX  TxPowerBackoff
    ACCESS  read-only
    STATUS  mandatory
    DESCRIPTION
    "Tx Power Back off"
::= {ltePhyEvents 2}

    TxPowerBackoff ::= INTEGER(0..128)

-- This log is generated each random access attempt
message3Report OBJECT-TYPE
    SYNTAX  Message3Report
    ACCESS  read-only
    STATUS  mandatory
    DESCRIPTION
    "Message 3 Report"
::= {ltePhyEvents 3}

    Message3Report ::= SEQUENCE {
        tpc                         INTEGER,
        mcs                         MCS,
        resourceIndicatorValue      INTEGER,
        cqi                         CqiSubValue,
        uplinkDelay                 BOOLEAN,
        hoppingFlag                 HoppingFlag,
        msg3SysFrameNumber          SystemFrameNumber,
        msg3SubFrameNumber          SubFrameNumber,
        numRb                       INTEGER(1..100),
        transportBlockSizeIndex     INTEGER(0..26),
        modulationType              ModulationType,
        redundancyVersionIndex      INTEGER(0..3),
        harqId                      INTEGER(0..7)
    }

        -------------------------------------------------------------------------------
        ------      mdmiLte Physical Layer Events                          ------------
        -------------------------------------------------------------------------------
        -------------------------------------------------------------------------------
        ------      mdmiLte Physical Layer PMCH                            ------------
        -------------------------------------------------------------------------------
-- This log shall be reported when 20 records/measurements have been collected, or when 500ms have passed from the previous OID log timestamp, whichever happens first. Each record/measurement shall be reported as and when a change occurs
pmchReport OBJECT-TYPE
    SYNTAX  PmchReport
    ACCESS  read-only
    STATUS  mandatory
    DESCRIPTION
    "PMCH Report"
::= {ltePhyPmch 1}

    PmchReport ::= SEQUENCE OF PmchReportInfo

    PmchReportInfo ::= SEQUENCE {
        systemFrameNumber   SystemFrameNumber,
        subFrameNumber      SubFrameNumber,
        pmchs       SEQUENCE OF PMCH   -- PMCHs in each MBSFN area, should be updated when related SIB changes
    }

    PMCH ::= SEQUENCE {
        bler    INTEGER,                -- BLER for PMCH being consumed, represented as a percentage value less than 100
        mtchs   SEQUENCE OF MTCH        -- MTCHs on each PMCH
    } 

    MTCH ::= SEQUENCE {
        dataRate        INTEGER,        -- Data rate on each MTCH, in Kbps
        tmgi            TMGI            -- TMGI of each MTCH to be updated when SIB changes
    }

-- {ltePhyPmch 2} reserved for PMCH Stats

-- This log shall be reported when 20 records/measurements have been collected, or when 500ms have passed from the previous OID log timestamp, whichever happens first. Each record/measurement shall be reported as and when a change occurs
pmchDecodingResults OBJECT-TYPE
    SYNTAX  PmchDecodingResults
    ACCESS  read-only
    STATUS  mandatory
    DESCRIPTION
    "PMCH Decoding Results"
::= {ltePhyPmch 3}

    PmchDecodingResults ::= SEQUENCE OF PmchDecodingResult

    PmchDecodingResult ::= SEQUENCE {
        systemFrameNumber   SystemFrameNumber,
        subFrameNumber      SubFrameNumber,
        servingCellIndex    ServingCellIndex,
        pmchId              INTEGER (0..255),
        areaId              INTEGER (0..255),  
        numRBs              INTEGER (0..110),   -- number of resource blocks
        numOfLayers         INTEGER (1..4),
        transportblocks     SEQUENCE OF PmchTransportBlock         
    }
    
    PmchTransportBlock ::= SEQUENCE {
        harqId              INTEGER(0..14), -- Harq ID 36.213 section 7. Up to 8 for FDD (0-7), up to 15 for TDD (0-14).
        redundancyVersion   INTEGER(0..3),
        newDataIndicator    INTEGER(0..1),                 
        crcResult           CrcResult,
        rntiType            RntiType,
        tbIndex             INTEGER(0..1),  -- Index for transport blocks when 2 transport blocks are received with the same rnti. Default 0.
        tbSize              INTEGER,        -- Transport block size in bytes
        mcs                 MCS,
        numRBs              INTEGER(0..255) -- number of resource blocks in each TB
    }

        -------------------------------------------------------------------------------
        ------      mdmiLte Physical Layer PBCH                            ------------
        -------------------------------------------------------------------------------
-- {ltePhyPbch 1} reserved for PBCH Report
-- {ltePhyPbch 2} reserved for PBCH Stats

-- This log shall be reported when 20 records/measurements have been collected, or when 500ms have passed from the previous OID log timestamp, whichever happens first. Each record/measurement shall be reported as and when a change occurs
pbchDecodingResults OBJECT-TYPE
    SYNTAX  PbchDecodingResults
    ACCESS  read-only
    STATUS  mandatory
    DESCRIPTION
    "PBCH Decoding Results"
::= {ltePhyPbch 3}

    PbchDecodingResults ::= SEQUENCE OF PbchDecodingResultInfo

    PbchDecodingResultInfo ::= SEQUENCE {
        systemFrameNumber   SystemFrameNumber,
        subFrameNumber      SubFrameNumber,
        servingCellId       INTEGER (0..504),
        pbchDecode          PbchDecode,
        pbchDecodingResult  PbchDecodingResult,
        tx0Rx0Cir           Tx0Rx0Cir
    }

    PbchDecode ::= SEQUENCE {
        earfcn          Earfcn,
        crcResult       CrcResult,
        pbchPayload     INTEGER,            -- raw PBCH payload in bytes, invalid if crcPass is failed
        numAntennas     INTEGER(0..2),      -- 0->1, 1->2, 2->4
        sfn             SystemFrameNumber,  -- system frame number when pbch was decoded
        freqOffset      INTEGER,            -- frequencyOffset estimated based upon the PBCH decode
        dlBandwidth     INTEGER             -- the downlink bandwidth of a cell, in number of resource blocks
    }

    PbchDecodingResult ::= SEQUENCE {
        transmitAntennaConfig   INTEGER (0..2),         -- 0->1, 1->2, 2->4
        sfnOffset               INTEGER (0..7),
        crcResult               CrcResult        
    }

    Tx0Rx0Cir ::= SEQUENCE {        -- The length of real and imaginary values should be both N
        realValues          SEQUENCE OF INTEGER,
        imaginaryValues     SEQUENCE OF INTEGER
    }

        -------------------------------------------------------------------------------
        ------      mdmiLte Physical Layer PDSCH                           ------------
        -------------------------------------------------------------------------------

-- This log shall be reported when 20 records/measurements have been collected, or when 500ms have passed from the previous OID log timestamp, whichever happens first. Each record/measurement shall be reported as and when a change occurs
pdschReport OBJECT-TYPE
    SYNTAX  PdschReport
    ACCESS  read-only
    STATUS  mandatory
    DESCRIPTION
    "PDSCH Report"
::= {ltePhyPdsch 1}

    PdschReport ::= SEQUENCE OF PdschReportInfo

    PdschReportInfo ::= SEQUENCE {
        sysFrameNumber          SystemFrameNumber,
        subFrameNumber          SubFrameNumber,
        servingCellIndex        ServingCellIndex,
        resourceBlocks          INTEGER (1..110),
        mimoRankIndicator       INTEGER,           -- Number of Transport Blocks the UE can receive per Transmission Time Interval
        pdschDemodulationConfig PdschDemodulationConfig,
        pdschStatIndication     PdschStatIndication
    }

    PdschDemodulationConfig ::= SEQUENCE {
        modulationStream0   ModulationScheme,       -- Modulation type
        modulationStream1   PdschModulationStream   -- Modulation type, invalid when only 1 TB is received
    }

    PdschModulationStream ::= CHOICE {
        modulationStream-Invalid    NULL,               
        modulationStream1           ModulationScheme
    }

    PdschStatIndication ::= SEQUENCE {
        pmchId              INTEGER (0..255),
        areaId              INTEGER (0..255),
        pdschTb             SEQUENCE OF PdschTransportBlock     -- Either 1 or 2 TBs are received at a time
    }

    ModulationScheme ::= INTEGER {
        QPSK (0),
        QAM16 (1),
        QAM64 (2),
        QAM256 (3)
    }

    PdschTransportBlock ::= SEQUENCE {
        harqId                  INTEGER(0..14), -- Harq ID 36.213 section 7. Up to 8 for FDD (0-7), up to 15 for TDD (0-14).
        redundancyVersion       INTEGER(0..3),
        newDataIndicator        INTEGER(0..1),                 
        crcResult               CrcResult,
        rntiType                RntiType,
        tbIndex                 INTEGER(0..1),  -- Index for transport blocks when 2 transport blocks are received with the same rnti. Default 0.
        tbSize                  INTEGER,        -- Transport block size in bytes
        mcs                     MCS,
        duplicatePacket         INTEGER,           -- Number of duplicate packets. If ACK is changed to NACK during transmission due to an error, the transmitter assumes the receiver received a faulty packet and resends the packet (this would be a duplicate packet).
        harqCombining           HarqCombining,
        dlGrantMcsIndex         MCS,
        reTxNumber              INTEGER (1..8)         -- PDSCH HARQ process retransmition
    }

-- This log shall be reported when 20 records/measurements have been collected, or when 500ms have passed from the previous OID log timestamp, whichever happens first. Each record/measurement shall be reported as and when a change occurs
pdschStatistics OBJECT-TYPE
    SYNTAX  PdschStatisticsReport
    ACCESS  read-only
    STATUS  mandatory
    DESCRIPTION
    "PDSCH Statistics"
::= {ltePhyPdsch 2}

    PdschStatisticsReport ::= SEQUENCE OF PdschStatistics

    PdschStatistics ::= SEQUENCE {
        sysFrameNumber              SystemFrameNumber,
        subFrameNumber              SubFrameNumber,
        servingCellIndex            ServingCellIndex,
        pdschStatIndicationStats    PdschStatIndicationStats
    }

    PdschStatIndicationStats ::= SEQUENCE {
        numRBs          INTEGER (1..110),
        numLayers       INTEGER (1..4),
        numTbPresent    INTEGER (0..2)
    }

-- This log shall be reported when 20 records/measurements have been collected, or when 500ms have passed from the previous OID log timestamp, whichever happens first. Each record/measurement shall be reported as and when a change occurs
pdschDecodingResults OBJECT-TYPE
    SYNTAX  PdschDecodingResults
    ACCESS  read-only
    STATUS  mandatory
    DESCRIPTION
    "Pdsch Decoding Results"
::= {ltePhyPdsch 3}
    
    PdschDecodingResults ::= SEQUENCE {
        componentCarrierIndex       CarrierType,
        ueCategory                  INTEGER,
        transmissionMode            TransmissionMode,
        decodingResults             SEQUENCE OF PdschDecodingResult
    }

    PdschDecodingResult ::= SEQUENCE {
        sysFrameNumber          SystemFrameNumber,
        subFrameNumber          SubFrameNumber,
        servingCellId           INTEGER (0..504),
        servingCellIndex        ServingCellIndex,
        harqId                  INTEGER (0..14),
        pdschChannelId          INTEGER,                -- The value of RNTI
        streams                 SEQUENCE OF PdschDecodingStream
    }

    PdschDecodingStream ::= SEQUENCE {
        transportBlockCrc                   CrcResult,              -- CRC check result of the traspot block during the HARQ process in PDSCH channel
        ndi                                 INTEGER (0..1),
        reTxNumber                          INTEGER (1..8),         -- PDSCH HARQ process retransmition number values from first, …, eighth.
        codeBlockSizePlus                   INTEGER (0..6168),      -- maximum code block size
        codeBlockSizeMinus                  INTEGER (0..6168),
        numCodeBlockPlus                    INTEGER (0..13),
        numCodeBlockMinus                   INTEGER (0..13),
        redundancyVersionIndex              INTEGER,
        turboDecoderMaxIterationNumber      INTEGER,
        harqCombining                       HarqCombining,
        codewordIndex                       INTEGER,
        turboDecoderIterationsNumber        INTEGER,
        codeBlockCrcBitmask                 INTEGER,                -- Code block CRC bitmask. For the largest TB it is a bitmap of 13 bits (b12 b11 … b1 b0)
        earlyTerminationAlgorithm           BOOLEAN
    }

        -------------------------------------------------------------------------------
        ------      mdmiLte Physical Layer PCFICH                          ------------
        -------------------------------------------------------------------------------
-- {ltePhyPcfich 1} reserved for pcfichReport
-- {ltePhyPcfich 2} reserved for pcfichStatistics

-- This log shall be reported when 20 records/measurements have been collected, or when 500ms have passed from the previous OID log timestamp, whichever happens first. Each record/measurement shall be reported as and when a change occurs
pcfichDecodingResults OBJECT-TYPE
    SYNTAX  PcfichDecodingResults
    ACCESS  read-only
    STATUS  mandatory
    DESCRIPTION
    "PCFICH Decoding Results"
::= {ltePhyPcfich 3}

    PcfichDecodingResults ::= SEQUENCE OF PcfichDecodingResult

    PcfichDecodingResult ::= SEQUENCE {
        sysFrameNumber          SystemFrameNumber,
        subFrameNumber          SubFrameNumber,
        servingCellId           INTEGER (0..504),
        cfi                     INTEGER,
        componentCarrierIndex   CarrierType
    }

        -------------------------------------------------------------------------------
        ------      mdmiLte Physical Layer PDCCH                           ------------
        -------------------------------------------------------------------------------

-- This log shall be reported when 20 records/measurements have been collected, or when 500ms have passed from the previous OID log timestamp, whichever happens first. Each record/measurement shall be reported as and when a change occurs
pdcchReport OBJECT-TYPE
    SYNTAX  PdcchReport
    ACCESS  read-only
    STATUS  mandatory
    DESCRIPTION
    "PDCCH report"
::= {ltePhyPdcch 1}
    
    PdcchReport ::= SEQUENCE {
        duplexMode              DuplexType,
        ulDlConfig              INTEGER(0..6),
        searchSpace             SearchSpaceType,
        spsGrantType            SpsGrantType,
        indicationReport        SEQUENCE OF PdcchIndicationReport
    }   

    PdcchIndicationReport ::= SEQUENCE {
        sysFrameNumber          SystemFrameNumber,
        subFrameNumber          SubFrameNumber,
        servingCellId           INTEGER (0..504),
        servingCellIndex        ServingCellIndex,
        rntiType                RntiType,
        pdcchPayloadSize        INTEGER (0..255),
        newDlTx                 INTEGER (0..1)         -- new DL transmission flag
    }

    SpsGrantType ::= INTEGER {
        Null (0),
        Release (1),
        Activation (2),
        CfgGrant (3),
        ReTx (4)
    }


-- This log shall be reported when 20 records/measurements have been collected, or when 500ms have passed from the previous OID log timestamp, whichever happens first. Each record/measurement shall be reported as and when a change occurs
pdcchStatistics OBJECT-TYPE
    SYNTAX  PdcchStatistics
    ACCESS  read-only
    STATUS  mandatory
    DESCRIPTION
    "PDCCH Statistics"
::= {ltePhyPdcch 2}
    
    PdcchStatistics ::= SEQUENCE {
        duplexMode              DuplexType,
        ulDlConfig              INTEGER(0..6),
        indicationStats         SEQUENCE OF PdcchIndicationStats    -- PDCCH of the pcell of the serving cell
    }   

    PdcchIndicationStats ::= SEQUENCE {
        sysFrameNumber          SystemFrameNumber,
        subFrameNumber          SubFrameNumber,
        numDlTbs                INTEGER (0..3)          -- number of DL transport blocks
    }

-- This log shall be reported when 20 records/measurements have been collected, or when 500ms have passed from the previous OID log timestamp, whichever happens first. Each record/measurement shall be reported as and when a change occurs
pdcchDecodingResult OBJECT-TYPE
    SYNTAX  PdcchDecodingResult
    ACCESS  read-only
    STATUS  mandatory
    DESCRIPTION
    "PDCCH Decoding Result"
::= {ltePhyPdcch 3}

    PdcchDecodingResult ::= SEQUENCE {
        hypotheses          Hypotheses
    }

    Hypotheses ::= SEQUENCE OF Hypothesis
    Hypothesis ::= SEQUENCE {
        sysFrameNumber          SystemFrameNumber,
        subFrameNumber          SubFrameNumber,
        servingCellId           INTEGER (0..504),
        servingCellIndex        ServingCellIndex,
        cecAggregationLevel     CecAggregationLevel,
        dciFormat               DciFormat,
        decodeStatus            RntiType,
        payloadSize             INTEGER,
        dciFormatStatus         DciFormatStatus,
        searchSpaceType         SearchSpaceType,
        startCceIndex           StartCceIndex,
        tailMatch               TailBitingDecoderStateMatch
    }

    DciFormatStatus ::= INTEGER {
        dciSuccess (1),
        dciError (2)
    }

    StartCceIndex ::= INTEGER (0..86)

    TailBitingDecoderStateMatch ::= INTEGER {
        Mismatch (0),
        Match (1)
    }

        -------------------------------------------------------------------------------
        ------      mdmiLte Physical Layer PHICH                           ------------
        -------------------------------------------------------------------------------

-- This log shall be reported when 20 records/measurements have been collected, or when 500ms have passed from the previous OID log timestamp, whichever happens first. Each record/measurement shall be reported as and when a change occurs
phichReport OBJECT-TYPE
    SYNTAX  PhichReport
    ACCESS  read-only
    STATUS  mandatory
    DESCRIPTION
    "PHICH report"
::= {ltePhyPhich 1}
    
    PhichReport ::= SEQUENCE {
        duplexMode              DuplexType,
        ulDlConfig              INTEGER(0..6),
        indicationReport        SEQUENCE OF PhichIndicationReport 
    }

    PhichIndicationReport ::= SEQUENCE {
        sysFrameNumber                SystemFrameNumber,
        subFrameNumber                SubFrameNumber,
        phichValueIncluded            PhichIncluded,
        phich1ValueIncluded           PhichIncluded
    }

    PhichIncluded ::= CHOICE {
        phichValueNotIncluded        NULL,               
        phichValueIncluded           PhichValue
    }

    PhichValue ::= INTEGER {
        nak(0),
        ack(1)
    }

-- {ltePhyPhich 2} reserved for phichStats

-- This log shall be reported when 20 records/measurements have been collected, or when 500ms have passed from the previous OID log timestamp, whichever happens first. Each record/measurement shall be reported as and when a change occurs
phichDecodingResults OBJECT-TYPE
    SYNTAX  PhichDecodingResults
    ACCESS  read-only
    STATUS  mandatory
    DESCRIPTION
    "PHICH decoding results"
::= {ltePhyPhich 3}
    
    PhichDecodingResults ::= SEQUENCE {
        servingCellId               INTEGER (0..504),
        componentCarrierIndex       CarrierType,
        decodingResults             SEQUENCE OF PhichDecodingResult
    }

    PhichDecodingResult ::= SEQUENCE {
        sysFrameNumber          SystemFrameNumber,
        subFrameNumber          SubFrameNumber,
        phichResult0            PhichResultEnabled,         -- FDD and TDD all UL/DL configurations
        phichResult1            PhichResultEnabled          -- For TDD UL/DL configuration0 and PUSCH transmission in SF4 or SF0.
    }

    PhichResultEnabled ::= CHOICE {
        phichResultDisabled        NULL,               
        phichResultEnabled         PhichResult
    }

    PhichResult ::= SEQUENCE {
        decodingResult         PhichDecodingOutcome,
        spreadingCodeIndex     INTEGER (0..7), 
        phichGroupNum          INTEGER (0..31)
    }

    PhichDecodingOutcome ::= INTEGER {
        nak(0),
        ack(1)
    }

        -------------------------------------------------------------------------------
        ------      mdmiLte Physical Layer PUCCH                           ------------
        -------------------------------------------------------------------------------

-- This log shall be reported when 20 records/measurements have been collected, or when 500ms have passed from the previous OID log timestamp, whichever happens first. Each record/measurement shall be reported as and when a change occurs
pucchReport OBJECT-TYPE
    SYNTAX  PucchReport
    ACCESS  read-only
    STATUS  mandatory
    DESCRIPTION
    "PUCCH Report"
::= {ltePhyPucch 1}
        
    PucchReport ::= SEQUENCE OF PucchReportRecord

    PucchReportRecord ::= SEQUENCE {
        sysFrameNumber              SystemFrameNumber,
        subFrameNumber              SubFrameNumber,
        servingCellId               INTEGER (0..504),
        pucchTxReport               PucchTxReport,
        pucchGeneralTxParameters    PucchGeneralTxParameters
    }

    PucchTxReport ::= SEQUENCE {
        format              DciFormat,
        pucchDigitalGain    INTEGER,                            -- PUCCH digital amplitude gain in dB. Refer to P_PUCCH(i) defined in 3GPP TS 36.213 section 5.1.2.1.
        pucchTxPowerValue   PowerValue,                         -- PUCCH tx power
        pucchTpc            INTEGER (-9..27),                   -- TPC
        gi                  PowerControlAccumalationFactor      -- Power control accumalation factor
    }

    PucchGeneralTxParameters ::= SEQUENCE {
        startRbSlot0        INTEGER (0..110),
        startRbSlot1        INTEGER (0..110),
        dmrsSeqSlot0        INTEGER (0..29),
        dmrsSeqSlot1        INTEGER (0..29)  
    }

-- {ltePhyPucch 2} reserved for pucchStatistics

-- This log shall be reported when 20 records/measurements have been collected, or when 500ms have passed from the previous OID log timestamp, whichever happens first. Each record/measurement shall be reported as and when a change occurs
pucchPowerControl OBJECT-TYPE
    SYNTAX  PucchPowerControl
    ACCESS  read-only
    STATUS  mandatory
    DESCRIPTION
    "PUCCH Power Control"
::= {ltePhyPucch 3}

    PucchPowerControl ::= SEQUENCE OF PucchPowerControlRecord
    PucchPowerControlRecord ::= SEQUENCE {
        sysFrameNumber      SystemFrameNumber,
        subFrameNumber      SubFrameNumber,
        pucchTxPowerValue   PowerValue,                         -- PUCCH Tx power measurement in dB
        dciFormat           DciFormat,                          -- DCI format of the decoded PDCCH
        pucchTxFormatType   PucchTxFormatType,                  -- Pucch Tx Format Type            
        numHarqBits         INTEGER (0..2),                     -- Number of Harq bits
        pucchTpc            INTEGER (-9..27),                   -- TPC
        numCqiBits          INTEGER,                            -- Number of CQI bits
        dlPathLoss          INTEGER (0..255),                   -- Downlink path loss calculated in UE
        gi                  PowerControlAccumalationFactor      -- Power control accumalation factor     
    }

    PucchTxFormatType ::= INTEGER {
        format1 (0),
        format1A (1),
        format1B (2),
        format2 (3),
        format2A (4),
        format2B (5)
    }

-- This log shall be reported when 20 records/measurements have been collected, or when 500ms have passed from the previous OID log timestamp, whichever happens first. Each record/measurement shall be reported as and when a change occurs
pucchCsf OBJECT-TYPE
    SYNTAX  PucchCsfs
    ACCESS  read-only
    STATUS  mandatory
    DESCRIPTION
    "PUCCH CSF"
::= {ltePhyPucch 4}

    PucchCsfs ::= SEQUENCE OF PucchCsf

    PucchCsf ::= SEQUENCE {
        startSysFrameNumber     SystemFrameNumber,
        startSubFrameNumber     SubFrameNumber,
        csfTxMode               TransmissionMode,
        pucchReportingMode      PucchReportingMode,
        pucchReportType         PucchReportType,
        sizeBwp                 INTEGER (0..4),     -- Nj (number of sub-bands within a bandwidth part) as defined in 3GPP TS 36.213 section 7.2.2
        bwpIndex                INTEGER (0..4),     -- j (bandwidth part number) as defined in 3GPP TS 36.213 section 7.2.2
        subBandNum              INTEGER (1..14),    -- The sub-band number for which CSI has been reported over PUCCH in current sub-frame in case of UE selected sub-band feedback
        rankIndex               INTEGER(0..1),      -- 0: Rank 1  1: Rank 2. RI of the serving cell only         
        cqiCw0                  CqiSubValue,        -- The absolute code word CQI value should be used. CQI of the serving cell only
        cqiCw1                  CqiSubValue,        -- The absolute code word CQI value should be used. CQI of the serving cell only
        widebandPmi             INTEGER (0..15),
        componentCarrierIndex   CarrierType
    }

    PucchReportingMode ::= INTEGER {
        mode10 (0),
        mode11 (1),
        mode20 (2),
        mode21 (3)
    }

    PucchReportType ::= INTEGER {
        subBandCqiFeedback (0),
        wideBandCqiPmiFeedback (1),
        riFeedback (2),
        widebandCqiFeedback (3)
    }

    CqiSubValue ::= INTEGER (0..15)     
        -------------------------------------------------------------------------------
        ------      mdmiLte Physical Layer PUSCH                           ------------
        -------------------------------------------------------------------------------
-- This log shall be reported when 20 records/measurements have been collected, or when 500ms have passed from the previous OID log timestamp, whichever happens first. Each record/measurement shall be reported as and when a change occurs
puschReport OBJECT-TYPE
    SYNTAX  PuschReport
    ACCESS  read-only
    STATUS  mandatory
    DESCRIPTION
    "PUSCH Report"
::= {ltePhyPusch 1}
        
    PuschReport ::= SEQUENCE OF PuschReportRecord

    PuschReportRecord ::= SEQUENCE {
        sysFrameNumber              SystemFrameNumber,
        subFrameNumber              SubFrameNumber,
        servingCellId               INTEGER (0..504),
        puschTxReport               PuschTxReport,
        puschGeneralTxParameters    PuschGeneralTxParameters,
        harqId                      INTEGER (0..7)
    }

    PuschTxReport ::= SEQUENCE {
        puschDigitalGain    INTEGER,                            -- PUSCH digital amplitude gain in dB. Refer to P_PUSCH_c (i) defined in 3GPP TS 36.213 section 5.1.1.1
        puschTxPowerValue   PowerValue,                         -- PUSCH tx power
        puschTpc            INTEGER (-6..8),                    -- PUSCH TPC
        fi                  PowerControlAccumalationFactor,     -- Power control accumalation factor
        tbSize              INTEGER,                            -- Transport block size in bytes
        dlPathLoss          INTEGER (0..255)                    -- Downlink path loss calculated in UE
    }

    PuschGeneralTxParameters ::= SEQUENCE {
        ackExists                   BOOLEAN,
        cqiExists                   BOOLEAN,
        riExists                    BOOLEAN,
        frequencyHopping            FrequencyHopping,             
        startRbSlot0                INTEGER (0..110),
        startRbSlot1                INTEGER (0..110),
        dmrsSeqSlot0                INTEGER (0..11),
        dmrsSeqSlot1                INTEGER (0..11),
        rbNum                       INTEGER (0..110),                 
        tbSize                      INTEGER,
        numAckBits                  INTEGER (0..7),             -- Length of ACK NACK raw payload
        numRiBits                   INTEGER (0..3),             -- Length of RI raw payload  
        numCqiBits                  INTEGER (0..66),            -- Length of CQI raw payload
        modOrder                    PuschModulationOrder,       -- Modulation order    
        retransmitIndex             INTEGER (1..28)             -- HARQ retransmission number   
    }

    FrequencyHopping ::= INTEGER {
        Disabled (0),
        InterSF (1),
        IntraPlusInter (2),
        Undefined (3)
    }

    PuschModulationOrder ::= INTEGER {
        BPSK (0),
        QPSK (1),
        QAM16 (2),
        QAM64 (3)
    }

-- {ltePhyPusch 2} reserved for puschStatistics

-- This log shall be reported when 20 records/measurements have been collected, or when 500ms have passed from the previous OID log timestamp, whichever happens first. Each record/measurement shall be reported as and when a change occurs
puschPowerControl OBJECT-TYPE
    SYNTAX  PuschPowerControl
    ACCESS  read-only
    STATUS  mandatory
    DESCRIPTION
    "PUSCH Power Control"
::= {ltePhyPusch 3}

    PuschPowerControl ::= SEQUENCE OF PuschPowerControlRecord
    PuschPowerControlRecord ::= SEQUENCE {
        sysFrameNumber      SystemFrameNumber,
        subFrameNumber      SubFrameNumber,
        puschTxPowerValue   PowerValue,                         -- PUSCH Tx power measurement in dB
        dciFormat           DciFormat,                          -- DCI format of the decoded PDCCH
        puschTxType         PuschTxType,                        -- Pusch Tx Type            
        rbNum               INTEGER (0..110),                   -- Number of allocated resource blocks in PUSCH
        tbSize              INTEGER,                            -- Transport block size in bytes
        dlPathLoss          INTEGER(0..255),                    -- Downlink path loss calculated in UE
        puschTpc            INTEGER (-6..8),                    -- PUSCH TPC
        fi                  PowerControlAccumalationFactor      -- Power control accumalation factor           
    }

    PuschTxType ::= INTEGER {
        semiPersistent (0),
        dynamic (1),
        rachMsg3 (2)
    }


-- This log shall be reported when 20 records/measurements have been collected, or when 500ms have passed from the previous OID log timestamp, whichever happens first. Each record/measurement shall be reported as and when a change occurs
puschCsf OBJECT-TYPE
    SYNTAX  PuschCsfs
    ACCESS  read-only
    STATUS  mandatory
    DESCRIPTION
    "PUSCH CSF"
::= {ltePhyPusch 4}

    PuschCsfs ::= SEQUENCE OF PuschCsf

    PuschCsf ::= SEQUENCE {
        startSysFrameNumber     SystemFrameNumber,
        startSubFrameNumber     SubFrameNumber,
        csfTxMode               TransmissionMode,
        puschReportingMode      PuschReportingMode,
        subBandNum              INTEGER(1..27),                 -- The sub-band number for which CSI has been reported over PUSCH in current sub-frame in case of UE selected sub-band feedback
        rankIndex               INTEGER(0..1),                  -- 0: Rank 1  1: Rank 2. RI of the serving cell only
        widebandCqiCw0          CqiSubValue,                    -- The absolute code word CQI value should be used. CQI of the serving cell only
        widebandCqiCw1          CqiSubValue,                    -- The absolute code word CQI value should be used. CQI of the serving cell only
        sizeM                   INTEGER,                        -- 3GPP TS 36.213 Table 7.2.1-5
        singleWbPmi             INTEGER(0..15),                 -- The Wideband PMI reported for aperiodic CSI reporting over PUSCH
        singleMbPmi             INTEGER(0..15),                 -- The single PMI value reported to network for UE selected preferred M sub-bands as a part of aperiodic CSI reporting
        subbandCqiCw0Sb         SEQUENCE OF CqiSubValue,        -- CQI CW0 for each subband. The length should be the value of subBandNum. The absolute code word CQI value should be used.
        mSubbandCqiCw0          CqiSubValue,                    -- The absolute code word CQI value should be used.
        subbandCqiCw1Sb         SEQUENCE OF CqiSubValue,        -- CQI CW1 for each subband. The length should be the value of subBandNum. The absolute code word CQI value should be used.
        mSubbandCqiCw1          CqiSubValue,                    -- The absolute code word CQI value should be used.
        subBandSizeK            INTEGER,
        componentCarrierIndex   CarrierType
    }

    PuschReportingMode ::= INTEGER {
        modeAperiodicRm12 (0),
        modeAperiodicRm20 (1),
        modeAperiodicRm22 (2),
        modeAperiodicRm30 (3),
        modeAperiodicRm31 (4)
    }

        -------------------------------------------------------------------------------
        ------      mdmiLte Physical Layer PRACH                           ------------
        -------------------------------------------------------------------------------

-- This log is generated every RA Attampt
prachReport OBJECT-TYPE
    SYNTAX  PrachReport
    ACCESS  read-only
    STATUS  mandatory
    DESCRIPTION
    "PRACH report"
::= {ltePhyPrach 1}

    PrachReport ::= SEQUENCE {
        sysFrameNumber          SystemFrameNumber,
        subFrameNumber          SubFrameNumber,
        rachTxPower             INTEGER (-112..23),     -- PRACH tx power in dB 
        zadOffSeqNum            INTEGER (0..837),       -- ZadOFF Sequence Number
        prachConfig             INTEGER (0..64),        -- Random access preamble timing for a range of preamble formats
        preambleFormat          INTEGER (0..4),         -- Preamble Format
        duplexType              DuplexType,
        maxTransmissionMsg3     INTEGER (1..8),         -- Max number of HARQ re-transmissions from UE for RACH message 3
        raResponseWindowSize    INTEGER (2..10),        -- Window size for reception of RACH message 2
        rachRequestResult       RachRequestResult       -- RACH Request success for failure
    }

    RachRequestResult ::= INTEGER {
        success (0),
        failure (1)
    }

        -------------------------------------------------------------------------------
        ------      mdmiLte Physical Layer EPDCCH                          ------------
        -------------------------------------------------------------------------------


    -------------------------------------------------------------------------------
    ------      mdmiLte IP                                             ------------
    -------------------------------------------------------------------------------
        -------------------------------------------------------------------------------
        ------      mdmiLte IP KPIs                                        ------------
        -------------------------------------------------------------------------------

ipThroughputDL OBJECT-TYPE
-- Downlink throughput measured by the UE during an ftp-download session, on the IP sub-layer
-- IP packet payload defined by RFC 791 and RFC 2460
    SYNTAX  ThroughputObject
    ACCESS  read-only
    STATUS  mandatory
    DESCRIPTION
    "Downlink throughput measured by the UE on the IP sub-layer. Object is time-stamped and geo-referenced."
::= {lteIpKpis 1}

ipThroughputUL OBJECT-TYPE
-- Uplink throughput measured by the UE during an ftp-download session, on the IP sub-layer
-- IP packet payload defined by RFC 791 and RFC 2460
    SYNTAX  ThroughputObject
    ACCESS  read-only
    STATUS  mandatory
    DESCRIPTION
    "Uplink throughput measured by the UE on the IP sub-layer. Object is time-stamped and geo-referenced."
::= {lteIpKpis 2}

        -------------------------------------------------------------------------------
        ------      mdmiLte IP Events                                      ------------
        -------------------------------------------------------------------------------
    
-- This event will be logged every time when a LTE to WiFi handover attempt or response occurs during a call
lteToWifiHandoverEvent OBJECT-TYPE
    SYNTAX  LteToWifiHandover
    ACCESS  read-only
    STATUS  mandatory
    DESCRIPTION
    "LTE to WiFi Handover Event"
::= {lteIpEvents 1}

LteToWifiHandover ::= CHOICE {
    handoverAttempt     NULL,
    handoverResult      LteToWifiHOResult
}

LteToWifiHOResult ::= SEQUENCE {
    epdgIpAddress       OCTET STRING,
    result              CHOICE {
        success         LteToWifiHOSuccess,
        failure         LteToWifiHOFailure
    }
}

LteToWifiHOSuccess ::= SEQUENCE {
    accessPointName     OCTET STRING,
    callMode            LteToWifiHOCallMode
}

LteToWifiHOCallMode ::= INTEGER {
    idle (0),
    active (1)
}

LteToWifiHOFailure ::= CHOICE {
    ipsecTimeoutFailure         NULL,
    ipsecFailureErrorCode       IPSecFailureErrorCode
}

IPSecFailureErrorCode ::= INTEGER {
    UNSUPPORTED_CRITICAL_PAYLOAD (1),
    INVALID_IKE_SPI (4),
    INVALID_MAJOR_VERSION (5),
    INVALID_SYNTAX (7),
    INVALID_MESSAGE_ID (9),
    INVALID_SPI (11),
    NO_PROPOSAL_CHOSEN (14),
    INVALID_KE_PAYLOAD (17),
    AUTHENTICATION_FAILED (24),
    SINGLE_PAIR_REQUIRED (34),
    NO_ADDITIONAL_SAS (35),
    INTERNAL_ADDRESS_FAILURE (36),
    FAILED_CP_REQUIRED (37),
    TS_UNACCEPTABLE (38),
    INVALID_SELECTORS (39),
    UNACCEPTABLE_ADDRESSES (40),
    UNEXPECTED_NAT_DETECTED (41),
    TEMPORARY_FAILURE (43),
    CHILD_SA_NOT_FOUND (44),
    NO_SUBSCRIPTION (9000),
    NETWORK_TOO_BUSY (10000),
    NETWORK_FAILURE (10500),
    ROAMING_NOT_ALLOWED (11000),
    RAT_DISALLOWED (11001)
}

        -------------------------------------------------------------------------------
        ------      mdmiLte IP Messages                                    ------------
        -------------------------------------------------------------------------------

-- IP Packets, header defined by RFC 791 and RFC 2460
-- Note: IPv6 jumbograms (size > 65536) not supported
-- Default IP Header logging: includes entire IP header only, regardless of embedded stream type (egs UDP/TCP/RTP/SIP)
ip-OTA-Packet OBJECT-TYPE
    SYNTAX  IpPacketReport
    ACCESS  read-only
    STATUS  mandatory
    DESCRIPTION
    "IP OTA Packet"
::= {lteIpMessages 1}

    IpPacketReport ::= SEQUENCE {
        ip-version  IpVersion,
        direction   OtaMessageDirection,
        ipPayload   OCTET STRING(SIZE (1..65536)) 
    }
    IpVersion ::= INTEGER {
        ipv4 (1),
        ipv6 (2)
    }

-- SIP Messages from RFC 3261
-- SIP , includes IP header , TCP/UDP header, SIP payload plus options
sip-OTA-Message OBJECT-TYPE
    SYNTAX  SipMessageReport
    ACCESS  read-only
    STATUS  mandatory
    DESCRIPTION
    "SIP OTA Message"
::= {lteIpMessages 2}

    SipMessageReport ::= SEQUENCE {
        direction   OtaMessageDirection,
        sipPayload  OCTET STRING(SIZE (1..8192)) 
    }

-- RTP Messages from RFC 3550
-- RTP (only header), includes IP header/TCP/UDP header and the RTP header
rtp-OTA-Message OBJECT-TYPE
    SYNTAX  RtpMessageReport
    ACCESS  read-only
    STATUS  mandatory
    DESCRIPTION
    "RTP OTA Message"
::= {lteIpMessages 3}

    RtpMessageReport ::= SEQUENCE {
        direction   OtaMessageDirection,
        rtpPayload  OCTET STRING(SIZE (1..8192)) 
    }

-- IP Packets, header defined by RFC 791 and RFC 2460
-- Note: IPv6 jumbograms (size > 65536) not supported
-- Entire IP header plus payload, only for engg builds
ipOtaPacketWithPayload OBJECT-TYPE
    SYNTAX  IpPacketReport
    ACCESS  read-only
    STATUS  mandatory
    DESCRIPTION
    "IP OTA Packet"
::= {lteIpMessages 4}

-- includes IP header , TCP/UDP header, DNS message payload
dns-OTA-Message OBJECT-TYPE
    SYNTAX  DnsMessageReport
    ACCESS  read-only
    STATUS  mandatory
    DESCRIPTION
    "DNS Message"
::= {lteIpMessages 5}

    DnsMessageReport ::= SEQUENCE {
        ip-version          IpVersion,
        direction           OtaMessageDirection,
        dnsPayload          OCTET STRING(SIZE (1..65536)) 
    }


 -------------------------------------------------------------------------------
    ------      mdmiLte SUPL                                             ------------
    -------------------------------------------------------------------------------
        -------------------------------------------------------------------------------
        ------      mdmiLte SUPL KPIs                                        ------------
        -------------------------------------------------------------------------------
-- This log is generated every 500ms
suplStatistics OBJECT-TYPE
    SYNTAX  SuplStatistics
    ACCESS  read-only
    STATUS  mandatory
    DESCRIPTION
    "SUPL Statistics"
::= {lteSuplKpis 1}

    SuplStatistics ::= SEQUENCE {
        numSuplInit                                 INTEGER,                -- Number of SUPL INIT messages sent to device
        numSuplPosInit                              INTEGER,                -- Number of SUPL POS INIT messages sent by device
        numSuplPos                                  INTEGER,                -- Number of SUPL POS messages sent to device
        averageTimeBetweenSuplPosInitAndSuplInit    INTEGER,                -- Average time difference between SUPL POS INIT response sent by device and the immediately preceding SUPL INIT sent to device
        miniTimeBetweenSuplPosInitAndSuplInit       INTEGER,                -- Minimum time difference between SUPL POS INIT response sent by device and the immediately preceding SUPL INIT sent to device
        maxTimeBetweenSuplPosInitAndSuplInit        INTEGER,                -- Maximum time difference between SUPL POS INIT response sent by device and the immediately preceding SUPL INIT sent to device
        averageTimeBetweenSuplPosAndSuplInit        INTEGER,                -- Average time difference between SUPL POS message response sent by device and the immediately preceding SUPL POS sent to device
        miniTimeBetweenSuplPosAndSuplInit           INTEGER,                -- Minimum time difference between SUPL POS message response sent by device and the immediately preceding SUPL POS sent to device
        maxTimeBetweenSuplPosAndSuplInit            INTEGER                 -- Maximum time difference between SUPL POS message response sent by device and the immediately preceding SUPL POS sent to device
    }

        -------------------------------------------------------------------------------
        ------      mdmiLte SUPL Events                                      ------------
        -------------------------------------------------------------------------------
    

        -------------------------------------------------------------------------------
        ------      mdmiLte SUPL Messages                                    ------------
        -------------------------------------------------------------------------------
-- This log is generated after any SUPL procedure
suplMessage OBJECT-TYPE
    SYNTAX  SuplMessage
    ACCESS  read-only
    STATUS  mandatory
    DESCRIPTION
    "SUPL Message"
::= {lteSuplMessages 1}

    SuplMessage ::= SEQUENCE {
        suplType                SuplType,
        rawMessage              OCTET STRING
    }

    SuplType ::= INTEGER {
        INIT(0),
        POS_INIT(1),
        POS(2),
        End(3)
    }


 -------------------------------------------------------------------------------
    ------      mdmiLte LPP                                             ------------
    -------------------------------------------------------------------------------
        -------------------------------------------------------------------------------
        ------      mdmiLte LPP KPIs                                        ------------
        -------------------------------------------------------------------------------
-- This log is generated every 500ms
lppStatistics OBJECT-TYPE
    SYNTAX  LppStatistics
    ACCESS  read-only
    STATUS  mandatory
    DESCRIPTION
    "LPP Statistics"
::= {lteLppKpis 1}

    LppStatistics ::= SEQUENCE {
        numRequest                      INTEGER,                -- Number of Request capabilities sent to device
        numRequestLocationInfoAndAck    INTEGER,                -- Number of Request location info sent to device and Acknowledgment sent by device pairs
        numRequestLocationInfo          INTEGER,                -- Number of request location info sent to device
        numProvide                      INTEGER,                -- Number of provide capabilities sent by device
        numProvideLocationInfoAndAck    INTEGER,                -- Number of provide location info sent by device and acknowledgment received by device pairs
        numProvideLocationInfo          INTEGER                 -- Number of provide location info sent by device
    }

        -------------------------------------------------------------------------------
        ------      mdmiLte LPP Events                                      ------------
        -------------------------------------------------------------------------------
    

        -------------------------------------------------------------------------------
        ------      mdmiLte LPP Messages                                    ------------
        -------------------------------------------------------------------------------

-- This log is generated after any LPP procedure
lppMessage OBJECT-TYPE
    SYNTAX  LppMessage
    ACCESS  read-only
    STATUS  mandatory
    DESCRIPTION
    "LPP Message"
::= {lteLppMessages 1}

    LppMessage ::= SEQUENCE {
        lppType                 LppType,
        rawMessage              OCTET STRING
    }

    LppType ::= INTEGER {
        Request_capabilities(0),
        Provide_capabilities(1),
        Provide_assistance_data(2),
        Request_location_info(3),
        Provide_location_info(4),
        Request_assistance_data(5),
        Acknowledgment(6)
    }


    -------------------------------------------------------------------------------
    ------      mdmiLte E911                                             ------------
    -------------------------------------------------------------------------------
        -------------------------------------------------------------------------------
        ------      mdmiLte E911 KPIs                                        ------------
        -------------------------------------------------------------------------------
-- This log is generated after any emergency attempts
emergencyCallStatistics OBJECT-TYPE
    SYNTAX  EmergencyCallStatistics
    ACCESS  read-only
    STATUS  mandatory
    DESCRIPTION
    "Emergency Call Statistics"
::= {lteE911Kpis 1}

    EmergencyCallStatistics ::= SEQUENCE {
        numEmergencyRegistrations                       INTEGER,                        -- Number of Emergency Registrations (SIP REGISTRATIONS of type SOS)
        numPse911Calls                                  INTEGER,                        -- number of PSe911 calls sent (count of SIP INVITE with 911: urn:service:sos)
        numPse922Calls                                  INTEGER,                        -- number of PSe922 calls sent (count of SIP INVITE with 922: sip:922@vzims.com)
        numSipCancel                                    INTEGER,                        -- number of SIP CANCEL messages sent after SIP INVITE for 911 or 922
        numSipBye                                       INTEGER,                        -- number of SIP BYE messages sent after a SIP INVITE for 911 or 922
        averageTimeDiffBetweenInviteAndOk               INTEGER,                        -- Average time difference between 200 OK for Invite (for 911 or 922) received by device and the immediately preceding SIP INVITE (for 911 or 922).
        minTimeDiffBetweenInviteAndOk                   INTEGER,                        -- Minimum time difference between 200 OK for Invite (for 911 or 922) received by device and the immediately preceding SIP INVITE (for 911 or 922).
        maxTimeDiffBetweenInviteAndOk                   INTEGER                         -- Maximum time difference between 200 OK for Invite (for 911 or 922) received by device and the immediately preceding SIP INVITE (for 911 or 922).
    }

        -------------------------------------------------------------------------------
        ------      mdmiLte E911 Events                                      ------------
        -------------------------------------------------------------------------------
    

        -------------------------------------------------------------------------------
        ------      mdmiLte E911 Messages                                    ------------
        -------------------------------------------------------------------------------

-------------------------------------------------------------------------------
------      mdmiGsm                                                ------------
-------------------------------------------------------------------------------
gsmDebug       OBJECT IDENTIFIER ::= { mdmiGsm 1 }
gsmNas         OBJECT IDENTIFIER ::= { mdmiGsm 2 }
gsmPhy         OBJECT IDENTIFIER ::= { mdmiGsm 3 }
gsmDataLink    OBJECT IDENTIFIER ::= { mdmiGsm 4 }
gsmRr          OBJECT IDENTIFIER ::= { mdmiGsm 5 }

gsmNasDebug             OBJECT IDENTIFIER ::= { gsmNas 1 }
gsmNasKpis              OBJECT IDENTIFIER ::= { gsmNas 2 }
gsmNasEvents            OBJECT IDENTIFIER ::= { gsmNas 3 }
gsmNasMessages          OBJECT IDENTIFIER ::= { gsmNas 4 }

gsmPhyDebug             OBJECT IDENTIFIER ::= { gsmPhy 1 }
gsmPhyKpis              OBJECT IDENTIFIER ::= { gsmPhy 2 }
gsmPhyEvents            OBJECT IDENTIFIER ::= { gsmPhy 3 }
gsmPhyMessages          OBJECT IDENTIFIER ::= { gsmPhy 4 }

gsmDataLinkDebug             OBJECT IDENTIFIER ::= { gsmDataLink 1 }
gsmDataLinkKpis              OBJECT IDENTIFIER ::= { gsmDataLink 2 }
gsmDataLinkEvents            OBJECT IDENTIFIER ::= { gsmDataLink 3 }
gsmDataLinkMessages          OBJECT IDENTIFIER ::= { gsmDataLink 4 }

gsmRrDebug             OBJECT IDENTIFIER ::= { gsmRr 1 }
gsmRrKpis              OBJECT IDENTIFIER ::= { gsmRr 2 }
gsmRrEvents            OBJECT IDENTIFIER ::= { gsmRr 3 }
gsmRrMessages          OBJECT IDENTIFIER ::= { gsmRr 4 }


    -------------------------------------------------------------------------------
    ------      mdmiGsm Common                                         ------------
    -------------------------------------------------------------------------------

Lai ::= OCTET STRING(SIZE (5))     -- Location Area Identity. Format: Public Land Mobile Network Identity 3 bytes / Location Area Code 2 bytes

    -------------------------------------------------------------------------------
    ------      mdmiGsm Debug                                          ------------
    -------------------------------------------------------------------------------
-- This log is generated every 1s
gsmStatusReport OBJECT-TYPE
    SYNTAX  GsmStatusReport
    ACCESS  read-only
    STATUS  mandatory
    DESCRIPTION
    "GSM Status Report"
::= {gsmDebug 1}

    GsmStatusReport ::= SEQUENCE {
        data                        OCTET STRING,               -- Date of formal release for phone executable
        time                        TimeStamp,                  -- Time of formal release for phone executable
        mobileStationModel          INTEGER,                    -- Model number of this mobile station
        mobileStationClassmark2     OCTET STRING(SIZE (4)),     -- Last 4 bytes of Mobile Station Classmark 2
        mobileStationClassmark3     OCTET STRING(SIZE (13)),    -- Last 13 bytes of Mobile Station Classmark 3
        imei                        OCTET STRING(SIZE (9)),
        imsi                        OCTET STRING(SIZE (9)),
        lai                         Lai,
        cellId                      INTEGER,
        callManagementState         CallManagementState
    }

    CallManagementState ::= INTEGER {
        Null (0),
        Idle (1),
        OriginatingCall (2),
        Waiting (3),
        IncomingCall (4),
        OngoingCall (5)
    }

    -------------------------------------------------------------------------------
    ------      mdmiGsm Nas                                            ------------
    -------------------------------------------------------------------------------
        -------------------------------------------------------------------------------
        ------      mdmiGsm Nas KPIs                                       ------------
        -------------------------------------------------------------------------------
        -------------------------------------------------------------------------------
        ------      mdmiGsm Nas Events                                     ------------
        -------------------------------------------------------------------------------
gsmMmStateChangeEvent OBJECT-TYPE
    SYNTAX  GsmMmStates
    ACCESS  read-only
    STATUS  mandatory
    DESCRIPTION
    "Current GSM MM State and Substate"
::= {gsmNasEvents 1}

    -- Refer to 3GPP TS 24.008 Section 4.1.2.1 for more details
    GsmMmStates ::= SEQUENCE {
        mmState        MmStateType,
        mmSubstate     MmSubstateType,
        mmUpdateStatus MmUpdateStatus
    }

gsmGmmStateChangeEvent OBJECT-TYPE
    SYNTAX  GsmGmmStates
    ACCESS  read-only
    STATUS  mandatory
    DESCRIPTION
    "Current GSM GMM State and Substate"
::= {gsmNasEvents 2}

    GsmGmmStates ::= SEQUENCE {
        gmmState        GmmStateType,
        gmmSubstate     GmmSubstateType,
        gmmUpdateStatus GmmUpdateStatus
    }

        -------------------------------------------------------------------------------
        ------      mdmiGsm Nas Messages                                   ------------
        -------------------------------------------------------------------------------

    -------------------------------------------------------------------------------
    ------      mdmiGsm Phy                                            ------------
    -------------------------------------------------------------------------------
        -------------------------------------------------------------------------------
        ------      mdmiGsm Phy KPIs                                       ------------
        -------------------------------------------------------------------------------
-- This log is generated every 200ms
gsmRrCellSelectionAndReselection OBJECT-TYPE
    SYNTAX  GsmRrCellSelectionAndReselection
    ACCESS  read-only
    STATUS  mandatory
    DESCRIPTION
    "GSM RR cell selection and reselection parameters"
::= {gsmPhyKpis 1}

    GsmRrCellSelectionAndReselection ::= SEQUENCE {
        rxLevHysteresis                     INTEGER (0..14),                -- RxLev hysteresis for required cell reselection; range is 0 to 14 dB, with 2 dB steps
        maxTxPower                          INTEGER,                        -- unit in dBm
        minRxLev                            INTEGER,                        -- unit in dBm
        powerOffset                         INTEGER (0..6),                 -- range is 0 to 6 dB with 2 dB steps 
        newEstablishmentCauseIndicator      BOOLEAN,
        cellBarQualify                      BOOLEAN,
        c2ReselectionOffset                 INTEGER (0..126),               -- range is 0 to 126 dB with 2 dB steps
        penaltyTime                         INTEGER (20..620)               -- 20 sec step
    }

-- This log is generated every 200ms
gsmRrRachParameters OBJECT-TYPE
    SYNTAX  GsmRrRachParameters
    ACCESS  read-only
    STATUS  mandatory
    DESCRIPTION
    "GSM RR RACH parameters"
::= {gsmPhyKpis 2}

    GsmRrRachParameters ::= SEQUENCE {
        maxAllowedRetransmissions           INTEGER,
        cellBarAccess                       BOOLEAN,
        accessControlClass                  INTEGER                         -- Information pertaining to MS allowed accesss
    }

-- This log is generated every 200ms
gsmRrServingCellInformation OBJECT-TYPE
    SYNTAX  GsmRrServingCellInformation
    ACCESS  read-only
    STATUS  mandatory
    DESCRIPTION
    "GSM RR Serving Cell Information"
::= {gsmPhyKpis 3}

    GsmRrServingCellInformation ::= SEQUENCE {
        bcchArfcn               INTEGER (0..1023),
        bsic                    OCTET STRING(SIZE (2)),                 -- Base station identity code. First byte - PLMN color; Second byte - BS color
        cellId                  INTEGER,
        lai                     Lai,
        cellSelectionPriority   CellSelectionPriority,
        nccPermitted            BOOLEAN
    }

    CellSelectionPriority ::= INTEGER {
        Normal (0),
        Low (1),
        Barred (2)
    }

-- This log is generated every 200ms
gsm3gCellMeasurements OBJECT-TYPE
    SYNTAX  Gsm3gCellMeasurements
    ACCESS  read-only
    STATUS  mandatory
    DESCRIPTION
    "GSM 3G Dedicated cell measurements"
::= {gsmPhyKpis 4}

    Gsm3gCellMeasurements ::= SEQUENCE OF Gsm3gCellMeasurement

    Gsm3gCellMeasurement ::= SEQUENCE {
        cellIndex                   INTEGER,
        uarfcn                      INTEGER,                    -- UMTS carrier channel number
        scramblingCode              INTEGER(0..8191),
        diversity                   INTEGER(0..1),
        rssi                        INTEGER(-106..-21),
        energy                      INTEGER                     -- in units of dB
    }


        -------------------------------------------------------------------------------
        ------      mdmiGsm Phy Events                                     ------------
        -------------------------------------------------------------------------------
        -------------------------------------------------------------------------------
        ------      mdmiGsm Phy Messages                                   ------------
        -------------------------------------------------------------------------------
gsmL1EnhancedMessageMetrics OBJECT-TYPE
    SYNTAX  GsmL1EnhancedMessageMetrics
    ACCESS  read-only
    STATUS  mandatory
    DESCRIPTION
    "L1 Enhanced Message Metrics"
::= {gsmPhyMessages 1}

    GsmL1EnhancedMessageMetrics ::= SEQUENCE {
        tdmaFrameNumber                     INTEGER,
        channelName                         ChannelName,
        messageLength                       INTEGER,
        codecType                           GsmCodecType,
        dlActiveCodecSet                    ActiveCodecSet,
        ulActiveCodecSet                    ActiveCodecSet
    }

    ChannelName ::= SEQUENCE {
        traffic             Traffic,
        signaling           Signaling
    }

    Traffic ::= INTEGER {
        FullRate (1),
        HalfRate (2)
    }

    Signaling ::= SEQUENCE {
        broadcast           Broadcast,
        commonControl       CommonControl,
        dedicatedControl    DedicatedControl
    }

    Broadcast ::= INTEGER {
        BCCH (1),
        FCCH (2),
        SCH (3)
    }

    CommonControl ::= SEQUENCE {
        downlink            Downlink,
        uplink              Uplink
    }

    Downlink ::= INTEGER {
        PCH (1),
        AGCH (2)
    }

    Uplink ::= INTEGER {
        RACH (1)
    }

    DedicatedControl ::= INTEGER {
        SDCCH (1),
        FACCH (2),
        SACCH (3)
    }

    GsmCodecType ::= INTEGER {
        AMR_MODE_0475 (0),          -- 4.75 kbps
        AMR_MODE_0515 (1),          -- 5.15 kbps
        AMR_MODE_0590 (2),          -- 5.90 kbps
        AMR_MODE_0670 (3),          -- 6.70 kbps
        AMR_MODE_0740 (4),          -- 7.40 kbps
        AMR_MODE_0795 (5),          -- 7.95 kbps
        AMR_MODE_1020 (6),          -- 10.20 kbps
        AMR_MODE_1220 (7),          -- 12.20 kbps
        AMR_WB_MODE_0660 (8),       -- 6.60 kbps
        AMR_WB_MODE_0885 (9),       -- 8.85 kbps
        AMR_WB_MODE_1265 (10)       -- 12.65 kbps
    }

    ActiveCodecSet ::= INTEGER {
        AMR_MODE_0475 (0),          -- 4.75 kbps
        AMR_MODE_0515 (1),          -- 5.15 kbps
        AMR_MODE_0590 (2),          -- 5.90 kbps
        AMR_MODE_0670 (3),          -- 6.70 kbps
        AMR_MODE_0740 (4),          -- 7.40 kbps
        AMR_MODE_0795 (5),          -- 7.95 kbps
        AMR_MODE_1020 (6),          -- 10.20 kbps
        AMR_MODE_1220 (7)           -- 12.20 kbps
    }

    -------------------------------------------------------------------------------
    ------      mdmiGsm DataLink                                       ------------
    -------------------------------------------------------------------------------
        -------------------------------------------------------------------------------
        ------      mdmiGsm DataLink KPIs                                  ------------
        -------------------------------------------------------------------------------
        -------------------------------------------------------------------------------
        ------      mdmiGsm DataLink Events                                ------------
        -------------------------------------------------------------------------------
        -------------------------------------------------------------------------------
        ------      mdmiGsm DataLink Messages                              ------------
        -------------------------------------------------------------------------------
-- This log is generated every transmission of PH_DATA_REQ
l2TransmissionStatus OBJECT-TYPE
    SYNTAX  L2TransmissionStatus
    ACCESS  read-only
    STATUS  mandatory
    DESCRIPTION
    "L2 Transmission Status"
::= {gsmDataLinkMessages 1}

    L2TransmissionStatus ::= SEQUENCE {
        sapi                            Sapi,               -- Service access point identifier
        channelType                     ChannelType,
        sendStateVariable               INTEGER,
        ackStateVariable                INTEGER,
        receiveStateVariable            INTEGER,
        numRetransmissions              INTEGER,
        frameType                       FrameType,
        numSegments                     INTEGER
    }

    Sapi ::= INTEGER {
        SAPI0 (0),
        SAPI3 (3)
    }

    ChannelType ::= INTEGER {
        DCCH (0),
        SACCH (4)
    }

    FrameType ::= INTEGER {
        SABM (0),
        UA (1),
        DM (2),
        DISC (3),
        UI (4),
        I (5),
        RR (6),
        REJ (7),
        RNR (8)
    }

    -------------------------------------------------------------------------------
    ------      mdmiGsm Rr                                            ------------
    -------------------------------------------------------------------------------
        -------------------------------------------------------------------------------
        ------      mdmiGsm Rr KPIs                                        ------------
        -------------------------------------------------------------------------------
-- This log is generated every 200ms
gsmRrChannelConfiguration OBJECT-TYPE
    SYNTAX  GsmRrChannelConfiguration
    ACCESS  read-only
    STATUS  mandatory
    DESCRIPTION
    "GSM RR Channel Configuration"
::= {gsmRrKpis 1}

    GsmRrChannelConfiguration ::= SEQUENCE {
        numDedicatedChannels                    INTEGER,
        dtxIndicator                            BOOLEAN,
        maxAllowedTxPower                       INTEGER,
        startingTimeValid                       BOOLEAN,
        ciphered                                BOOLEAN,
        cipherAlgorithm                         INTEGER,
        channelConfigStructure                  ChannelConfigStructure
    }

    ChannelConfigStructure ::= SEQUENCE {
        channelName                 INTEGER {
                                        FullRateTraffic (0),
                                        HalfRateTraffic (1),
                                        SDCCH_4 (2),
                                        SDCCH_8 (3)
                                    },
        subChannelNumber            INTEGER,
        timeslotNumber              INTEGER,
        trainingSeqNum              INTEGER,
        hopping                     BOOLEAN,
        mobileAllocationIndexOffset INTEGER,
        hoppingSeqNum               INTEGER,
        frequencies                 FrequencyList              
    }

    FrequencyList ::= SEQUENCE OF FrequencyFormat

    FrequencyFormat ::= SEQUENCE {
        arfcn               Earfcn
    }

-- This log is generated every 2s
gsmRrNeighborCells OBJECT-TYPE
    SYNTAX  GsmRrNeighborCells
    ACCESS  read-only
    STATUS  mandatory
    DESCRIPTION
    "GSM RR Neighbor cells"
::= {gsmRrKpis 2}

    GsmRrNeighborCells ::= FrequencyList

        -------------------------------------------------------------------------------
        ------      mdmiGsm Rr Events                                      ------------
        -------------------------------------------------------------------------------
        -------------------------------------------------------------------------------
        ------      mdmiGsm Rr Messages                                    ------------
        -------------------------------------------------------------------------------
gsmRrSignalingMessage OBJECT-TYPE
    SYNTAX  GsmRrSignalingMessage
    ACCESS  read-only
    STATUS  mandatory
    DESCRIPTION
    ""
::= {gsmRrMessages 1}

    GsmRrSignalingMessage ::= SEQUENCE {
        rrMessageType               INTEGER,            -- Message type, as defined in GSM04.18, table 10.4.1
        rrProtocolError             RrProtocolError,
        rrlogicalChannelType        RrLogicalChannelType
    }

    RrProtocolError ::= CHOICE {
        noError         NULL,
        hasError        INTEGER {
            InvalidProtocolDiscriminator (0),
            InvalidMessage (1),
            InvalidIe (2),
            Other (3)
        }
    }

    RrLogicalChannelType ::= INTEGER {
        UL_DCCH (0),
        RACH (1),
        UL_SACCH (2),
        UL_SDCCH (3),
        ULJACCH (4),
        DL_DCCH (5),
        BCCH (6),
        CCCH (7),
        DL_SACCH (8),
        DL_SDCCH (9),
        DLJACCH (10)
    }

-------------------------------------------------------------------------------
------      mdmiUmts                                               ------------
-------------------------------------------------------------------------------
umtsDebug    OBJECT IDENTIFIER ::= { mdmiUmts 1 }
umtsNas      OBJECT IDENTIFIER ::= { mdmiUmts 2 }

umtsNasDebug             OBJECT IDENTIFIER ::= { umtsNas 1 }
umtsNasKpis              OBJECT IDENTIFIER ::= { umtsNas 2 }
umtsNasEvents            OBJECT IDENTIFIER ::= { umtsNas 3 }
umtsNasMessages          OBJECT IDENTIFIER ::= { umtsNas 4 }

    -------------------------------------------------------------------------------
    ------      mdmiUmts Nas                                            ------------
    -------------------------------------------------------------------------------
        -------------------------------------------------------------------------------
        ------      mdmiUmts Nas KPIs                                      ------------
        -------------------------------------------------------------------------------
-- This log is generated every 1s
umtsUeOperationConfig OBJECT-TYPE
    SYNTAX  UmtsUeOperationConfig
    ACCESS  read-only
    STATUS  mandatory
    DESCRIPTION
    "UMTS UE Operation Configuration"
::= {umtsNasKpis 1}

    UmtsUeOperationConfig ::= SEQUENCE {
        plmnSelectionMode               PlmnSelectionMode,  -- refer to 3GPP TS 23.122
        ueOperationMode                 UeOperationMode
    }

    PlmnSelectionMode ::= INTEGER {
        Automatic (0),
        Manual (1)
    }

    UeOperationMode ::= INTEGER {
        ClassA (0),
        ClassB (1),
        ClassC (2)
    }


-- This log is generated every 1s
umtsUeDynamicId OBJECT-TYPE
    SYNTAX  UmtsUeDynamicId
    ACCESS  read-only
    STATUS  mandatory
    DESCRIPTION
    "UMTS UE Dynamic ID"
::= {umtsNasKpis 2}

    UmtsUeDynamicId ::= SEQUENCE {
        tmsi            Tmsi,
        ptmsiSize       INTEGER             -- Packet TMSI Size
    }

    Tmsi ::= INTEGER {
        TMSI (0),
        PTMSI (1)
    }


-- This log is generated every 1s
umtsUeStaticId OBJECT-TYPE
    SYNTAX  UmtsUeStaticId
    ACCESS  read-only
    STATUS  mandatory
    DESCRIPTION
    "UMTS UE Static ID"
::= {umtsNasKpis 3}

    UmtsUeStaticId ::= SEQUENCE {
        imei                        OCTET STRING(SIZE (9)),
        imsi                        OCTET STRING(SIZE (9)),
        imeiSv                      OCTET STRING(SIZE (10))         
    }


-- This log is generated every 1s
umtsNasEplmnList OBJECT-TYPE
    SYNTAX  UmtsNasEplmnList
    ACCESS  read-only
    STATUS  mandatory
    DESCRIPTION
    "UMTS NAS EPLMN List"
::= {umtsNasKpis 4}

    UmtsNasEplmnList ::= SEQUENCE {
        rplmnId                 MCC-MNC,                -- Register PLMNs ID
        eplmnIdList             SEQUENCE OF MCC-MNC     -- Equivalent PLMNs IDs
    }


-- This log is generated every 1s
umtsNasMmConfig OBJECT-TYPE
    SYNTAX  UmtsNasMmConfig
    ACCESS  read-only
    STATUS  mandatory
    DESCRIPTION
    "UMTS NAS MM Configuration"
::= {umtsNasKpis 5}

    UmtsNasMmConfig ::= SEQUENCE {
        networkOperationMode                    NetworkOperationMode,               
        serviceType                             ServiceType,
        servingCellPlmnId                       MCC-MNC,
        servingCellLai                          Lai,
        servingCellRai                          OCTET STRING(SIZE (1)),                    -- Routing area identification
        availablePlmnList                       SEQUENCE OF MCC-MNC
    }

    NetworkOperationMode ::= INTEGER {
        Class1 (0),
        Class2 (1),
        Class3 (2)
    }

    ServiceType ::= INTEGER {
        NO_SERVICE (0),
        CS_ONLY (1),
        PS_ONLY (2),
        CS_PS_SERVICE (3),
        LIMITED_SERVICE (4)
    }


-- This log is generated every 1s
umtsNasPsConnectionManagementConfig OBJECT-TYPE
    SYNTAX  UmtsNasPsConnectionManagementConfig
    ACCESS  read-only
    STATUS  mandatory
    DESCRIPTION
    "UMTS NAS PS Connection Management Configuration"
::= {umtsNasKpis 6}

    UmtsNasPsConnectionManagementConfig ::= SEQUENCE OF PsConnectionConfig

    PsConnectionConfig ::= SEQUENCE {
        packetSwitchCallId              INTEGER,
        nsapiValue                      INTEGER
    }


-- This log is generated every 1s
umtsNasCallQos OBJECT-TYPE
    SYNTAX  UmtsNasCallQos
    ACCESS  read-only
    STATUS  mandatory
    DESCRIPTION
    "UMTS NAS Call QOS"
::= {umtsNasKpis 7}

    UmtsNasCallQos ::= SEQUENCE {
        connectionId                    INTEGER,
        delayClass                      DelayClass,
        reliabilityClass                ReliabilityClass,
        peakThroughput                  INTEGER,
        precedenceClass                 PrecedenceClass
    }

    DelayClass ::= INTEGER {
        SubscribedDelayClass (0),
        DelayClass1 (1),
        DelayClass2 (2),
        DelayClass3 (3),
        DelayClass4 (4)
    }

    ReliabilityClass ::= INTEGER {
        SubscribedReliabilityClass (0),
        Ack_GTP_LLC_RLC (1),
        UnAck_GTP_Ack_LLC_RLC_protected (2),
        UnAck_GTP_LLC_Ack_RLC_protected (3),
        UnAck_GTP_LLC_RLC_protected (4),
        UnAck_GTP_LLC_RLC_unprotected (5)
    }

    PrecedenceClass ::= INTEGER {
        SubscribedPrecedence (0),
        HighPriority (1),
        NormalPriority (2),
        LowPriority (3)
    }


-- This log is generated every 1s
umtsNasConnectionBearerConfig OBJECT-TYPE
    SYNTAX  UmtsNasConnectionBearerConfig
    ACCESS  read-only
    STATUS  mandatory
    DESCRIPTION
    "UMTS NAS Connection Bearer Config"
::= {umtsNasKpis 8}

    UmtsNasConnectionBearerConfig ::= SEQUENCE {
        connectionId                    INTEGER,
        duplexMode                      DuplexMode,
        numDataBit                      NumDataBit,
        numStopBit                      NumStopBit,
        transferMode                    TransferMode,
        maxTrafficChannels              INTEGER
    }

    DuplexMode ::= INTEGER {
        HalfDuplex (0),
        FullDuplex (1)
    }

    NumDataBit ::= INTEGER {
        Bits_7 (0),
        Bits_8 (1)
    }

    NumStopBit ::= INTEGER {
        Bits_1 (0),
        Bits_2 (1)
    }

    TransferMode ::= INTEGER {
        CircuitMode (0),
        PacketMode (1)
    }


-- This log is generated every 1s
umtsNasCsConnectionManagementCallReleaseInfo OBJECT-TYPE
    SYNTAX  UmtsNasCsConnectionManagementCallReleaseInfo
    ACCESS  read-only
    STATUS  mandatory
    DESCRIPTION
    "UMTS NAS CS Connection Management Call Release Info"
::= {umtsNasKpis 9}

    UmtsNasCsConnectionManagementCallReleaseInfo ::= SEQUENCE {
        circuitCallId           INTEGER
    }


-- This log is generated every 1s
umtsNasCsConnectionManagementCallChangeInfo OBJECT-TYPE
    SYNTAX  UmtsNasCsConnectionManagementCallChangeInfo
    ACCESS  read-only
    STATUS  mandatory
    DESCRIPTION
    "UMTS NAS CS Connection Management Call Change Info"
::= {umtsNasKpis 10}

    UmtsNasCsConnectionManagementCallChangeInfo ::= SEQUENCE {
        circuitCallId           INTEGER,
        multiPartyState         MultiPartyState,
        holdState               HoldState
    }

    MultiPartyState ::= INTEGER {
        idle (0),
        request (1),
        call_in_multi_party (2),
        split_request (3)
    }

    HoldState ::= INTEGER {
        idle (0),
        request (1),
        call_held (2),
        retrieve_request (3)
    }


-- This log is generated every 1s
umtsNasCsConnectionManagementCallSetupInfo OBJECT-TYPE
    SYNTAX  UmtsNasCsConnectionManagementCallSetupInfo
    ACCESS  read-only
    STATUS  mandatory
    DESCRIPTION
    "UMTS NAS CS Connection Management Call Setup Info"
::= {umtsNasKpis 11}

    UmtsNasCsConnectionManagementCallSetupInfo ::= SEQUENCE {
        circuitCallId                       INTEGER,
        streamId                            INTEGER(0..255),
        callControlState                    INTEGER,            -- See 24.008 Section 5.1.2.1 Call states all the mobile station side of the interface
        multiPartyState                     MultiPartyState,
        holdState                           HoldState,
        callType                            INTEGER(0..1),       -- 0: Voice Call    1: DataCall
        callDirection                       INTEGER(0..1),       -- 0: Mobile-terminated    1: Mobile-originated
        calledPartyBcdNumber                OCTET STRING,        -- See 24.008 Section 10.5.4.7 Calling party BCD number
        callingPartyBcdNumber               OCTET STRING         -- See 24.008 Section 10.5.4.9 Calling party BCD number
    }

        -------------------------------------------------------------------------------
        ------      mdmiUmts Nas Events                                    ------------
        -------------------------------------------------------------------------------

umtsGmmStateChangeEvent OBJECT-TYPE
    SYNTAX  UmtsGmmStates
    ACCESS  read-only
    STATUS  mandatory
    DESCRIPTION
    "Current GMM State and Substate"
::= {umtsNasEvents 1}

    -- Refer to 3GPP TS 24.008 Section 4.1.3.1 for more details
    UmtsGmmStates ::= SEQUENCE {
        gmmState        GmmStateType,
        gmmSubstate     GmmSubstateType,
        gmmUpdateStatus GmmUpdateStatus
    }

umtsMmStateChangeEvent OBJECT-TYPE
    SYNTAX  UmtsMmStates
    ACCESS  read-only
    STATUS  mandatory
    DESCRIPTION
    "Current MM State and Substate"
::= {umtsNasEvents 2}

    UmtsMmStates ::= SEQUENCE {
        mmState             MmStateType,
        mmSubState          MmSubstateType,
        mmUpdateStatus      MmUpdateStatus
    }

        -------------------------------------------------------------------------------
        ------      mdmiUmts Nas Messages                                  ------------
        -------------------------------------------------------------------------------
umtsNasOtaMessage OBJECT-TYPE
    SYNTAX  UmtsNasOtaMessage
    ACCESS  read-only
    STATUS  mandatory
    DESCRIPTION
    "UMTS NAS OTA Message"
::= {umtsNasMessages 1}

    UmtsNasOtaMessage ::= SEQUENCE {
        direction                   OtaMessageDirection,
        otaLength                      INTEGER,
        name                        OCTET STRING
    }


-------------------------------------------------------------------------------
------      mdmiWifi                                               ------------
-------------------------------------------------------------------------------
wifiDebug   OBJECT IDENTIFIER ::= { mdmiWifi 1 }
wifiIp      OBJECT IDENTIFIER ::= { mdmiWifi 2 }
wifiMac     OBJECT IDENTIFIER ::= { mdmiWifi 3}

wifiDebugKpis           OBJECT IDENTIFIER ::= { wifiDebug 1 }
wifiDebugEvents         OBJECT IDENTIFIER ::= { wifiDebug 2 }

wifiIpDebug             OBJECT IDENTIFIER ::= { wifiIp 1 }
wifiIpKpis              OBJECT IDENTIFIER ::= { wifiIp 2 }
wifiIpEvents            OBJECT IDENTIFIER ::= { wifiIp 3 }
wifiIpMessages          OBJECT IDENTIFIER ::= { wifiIp 4 }

wifiMacDebug             OBJECT IDENTIFIER ::= { wifiMac 1 }
wifiMacKpis              OBJECT IDENTIFIER ::= { wifiMac 2 }
wifiMacEvents            OBJECT IDENTIFIER ::= { wifiMac 3 }
wifiMacMessages          OBJECT IDENTIFIER ::= { wifiMac 4 }

        -------------------------------------------------------------------------------
        ------      mdmiWifi Debug KPIs                                    ------------
        -------------------------------------------------------------------------------
-- This log will be logged every 1s
wifiInfo OBJECT-TYPE
    SYNTAX  WifiInformation
    ACCESS  read-only
    STATUS  mandatory
    DESCRIPTION
    "WiFi Info"
::= {wifiDebugKpis 1}

-- This log will be logged every 1s
wifiInternetConnectionStatus OBJECT-TYPE
    SYNTAX  WifiInternetConnectionStatus
    ACCESS  read-only
    STATUS  mandatory
    DESCRIPTION
    "WiFi Internet Connection Status"
::= {wifiDebugKpis 2}

WifiInternetConnectionStatus ::= CHOICE {
    noWifiInternetConnection  NULL,
    wifiInternetConnected     WifiInternetConnected     
}

WifiInternetConnected ::= SEQUENCE {
    linkSpeed   INTEGER     -- in Mbps
}

        -------------------------------------------------------------------------------
        ------      mdmiWifi Debug Events                                  ------------
        -------------------------------------------------------------------------------
-- This event is reported at the end of "Wifi Scan" procedure. It includes the list of all the Access points scanned during the "Wifi Scan" procedure.
wifiScanEvent OBJECT-TYPE
    SYNTAX  WifiScan
    ACCESS  read-only
    STATUS  mandatory
    DESCRIPTION
    "WiFi Scan"
::= {wifiDebugEvents 1}

    WifiScan ::= SEQUENCE {
        timeScanStart           TimeStamp,
        timeScanEnd             TimeStamp,
        scannedChannelList      SEQUENCE OF WifiChannel,
        scanType                WifiScanType,
        scannedAccessPoints     SEQUENCE OF WifiAccessPoint
    }

    WifiChannel ::= SEQUENCE {
        wifiFrequency   WifiFrequency,
        channelNumber   INTEGER
    }

    WifiFrequency ::= INTEGER {
        freq-2_4-GHz (1),
        freq-3_6-GHz (2),
        freq-4_9-GHz (3),
        freq-5-GHz (4),
        freq-5_9GHz (5)
    }

    WifiScanType ::= INTEGER {
        passive (1),
        active (2)
    }

    WifiAccessPoint ::= SEQUENCE {
        bssid               OCTET STRING,
        ssid                OCTET STRING,
        operationChannel    WifiChannel,
        supportedRates      SEQUENCE OF INTEGER,  -- in Mbps
        security            WifiSecurityInfo,
        qosCapability       BOOLEAN,
        countryInfo         CountryInfo,
        htCapability        HTCapability
    }

    WifiSecurityInfo ::= INTEGER {
        WEP (1),
        WPA (2),
        WPA2 (3),
        WPA-CCMP (4),
        WPA-TKIP (5),
        WPA2-CCMP (6),
        WPA2-TKIP (7),
        WPA2-Enterprise (8)
    }

    CountryInfo ::= INTEGER {
        US (0),
        others (1)
    }

    -- Refer to the IEEE 802.11 document Section 8.4.2.59 HT Operation element
    HTCapability ::= SEQUENCE {
        channelWidth                STAChannelWidth,
        secondaryChannelOffset      SecondaryChannelOffset
    }

    STAChannelWidth ::= INTEGER {
        ChannelWidth20MHz (0),
        AnyChannelWidth   (1)      -- any channel width in the Supported channel width set
    }

    SecondaryChannelOffset ::= INTEGER {
        SCA (1),
        SCB (3),
        SCN (0)
        -- value 2 is reserved
    }

-- This event is logged when a WiFi Association occurs
wifiAssociationEvent OBJECT-TYPE
    SYNTAX  WiFiAssociationEvent
    ACCESS  read-only
    STATUS  mandatory
    DESCRIPTION
    "WiFi Association Event"
::= {wifiDebugEvents 2}

WiFiAssociationEvent ::= SEQUENCE {
    bssid   OCTET STRING,           -- MAC Address of the Access Point UE associated with
    ssid    OCTET STRING,           -- SSID of the Access Point UE associated with
    result  WifiResultCode
}

WifiResultCode ::= INTEGER {
    success (0),
    failure (1)
}

-- This event is logged when a WiFi Re-association occurs
wifiReAssociationEvent OBJECT-TYPE
    SYNTAX  WiFiReAssociationEvent
    ACCESS  read-only
    STATUS  mandatory
    DESCRIPTION
    "WiFi Re-Association Event"
::= {wifiDebugEvents 3}

WiFiReAssociationEvent ::= SEQUENCE {
    bssid   OCTET STRING,           -- MAC Address of the Access Point UE associated with
    ssid    OCTET STRING,           -- SSID of the Access Point UE associated with
    result  WifiResultCode
}

-- This event is logged when a WiFi Disconnection occurs
wifiDisconnectionEvent OBJECT-TYPE
    SYNTAX  WifiDisconnectionEvent
    ACCESS  read-only
    STATUS  mandatory
    DESCRIPTION
    "WiFi Disconnection Event"
::= {wifiDebugEvents 4}

WifiDisconnectionEvent ::= SEQUENCE {
    bssid       OCTET STRING,           -- MAC Address of the Access Point UE associated with
    ssid        OCTET STRING,           -- SSID of the Access Point UE associated with
    reasonCode  INTEGER (0..66)         -- Refer to IEEE 802.11-8.4.1.7
}

-- This event is logged when a WiFi Authentication occurs
wifiAuthenticationEvent OBJECT-TYPE
    SYNTAX  WiFiAuthenticationEvent
    ACCESS  read-only
    STATUS  mandatory
    DESCRIPTION
    "WiFi Authentication Event"
::= {wifiDebugEvents 5}

WiFiAuthenticationEvent ::= SEQUENCE {
    bssid   OCTET STRING,           -- MAC Address of the Access Point UE authenticated with
    result  WifiResultCode
}

-- This event is logged when a WiFi De-Authentication occurs
wifiDeAuthenticationEvent OBJECT-TYPE
    SYNTAX  WiFiDeAuthenticationEvent
    ACCESS  read-only
    STATUS  mandatory
    DESCRIPTION
    "WiFi De-Authentication Event"
::= {wifiDebugEvents 6}

WiFiDeAuthenticationEvent ::= SEQUENCE {
    bssid   OCTET STRING,               -- MAC Address of the Access Point UE authenticated with
    reasonCode  INTEGER (0..66)         -- Refer to IEEE 802.11-8.4.1.7
}

-- This event is logged when WiFi Power Save Mode on/off is triggered
wifiPowerSaveEvent OBJECT-TYPE
    SYNTAX  WifiPowerSaveEvent
    ACCESS  read-only
    STATUS  mandatory
    DESCRIPTION
    "WiFi Power Save Event"
::= {wifiDebugEvents 7}

WifiPowerSaveEvent ::= INTEGER {
    powerSaveModeOn (0),
    powerSaveModeOff (1)
}

-- This event is logged when a WiFi DHCP failure occurs
wifiDhcpFailureEvent OBJECT-TYPE
    SYNTAX  WifiDhcpFailureEvent
    ACCESS  read-only
    STATUS  mandatory
    DESCRIPTION
    "WiFi DHCP Failure Event"
::= {wifiDebugEvents 8}

WifiDhcpFailureEvent ::= SEQUENCE {
    failureReason   OCTET STRING(SIZE (0.. 20))
}

-- This event is logged when a WiFi DNS query or query response occurs
wifiDnsQueryEvent OBJECT-TYPE
    SYNTAX  WifiDnsQueryEvent
    ACCESS  read-only
    STATUS  mandatory
    DESCRIPTION
    "WiFi DNS Query Event"
::= {wifiDebugEvents 9}

WifiDnsQueryEvent ::= CHOICE {
    dnsQuery    NULL,
    dnsResult   WifiResultCode
}

-- This event is logged every time when a UDPENCAP Message is received
-- For both IPv4 and IPv6
wifiNatKeepAliveEvent OBJECT-TYPE
    SYNTAX  WifiNatKeepAliveEvent
    ACCESS  read-only
    STATUS  mandatory
    DESCRIPTION
    "WiFi NAT Keep Alive Event"
::= {wifiDebugEvents 10}


WifiNatKeepAliveEvent ::= SEQUENCE {
    natKeepAliveTimestamp TimeStamp         
}

-- This event is logged every time when there is a DPD message sent between ePDG and UE
wifiDpdIntervalEvent OBJECT-TYPE
    SYNTAX  WifiDpdIntervalEvent
    ACCESS  read-only
    STATUS  mandatory
    DESCRIPTION
    "WiFi NAT Keep Alive Event"
::= {wifiDebugEvents 11}


WifiDpdIntervalEvent ::= SEQUENCE {
    dpdInterval         INTEGER       -- Dead peer detection interval, in seconds        
}

        -------------------------------------------------------------------------------
        ------      mdmiWifi IP Events                                     ------------
        -------------------------------------------------------------------------------

-- This event will be logged every time when a WiFi to LTE handover attempt or response occurs during a call.
wifiToLTEHandoverEvent OBJECT-TYPE
    SYNTAX  WifiToLteHandover
    ACCESS  read-only
    STATUS  mandatory
    DESCRIPTION
    "WiFi to LTE Handover Event"
::= {wifiIpEvents 1}

WifiToLteHandover ::= CHOICE {
    handoverAttempt     NULL,
    handoverResult      WifiToLteHOResult
}

WifiToLteHOResult ::= SEQUENCE {
    epdgIpAddress       OCTET STRING,
    result              CHOICE {
        success         WifiToLteHOSuccess,
        failure         WifiToLteHOFailure
    }
}

WifiToLteHOSuccess ::= SEQUENCE {
    accessPointName     OCTET STRING,
    callMode            WifiToLteHOCallMode
}

WifiToLteHOCallMode ::= INTEGER {
    idle (0),
    active (1)
}

WifiToLteHOFailure ::= INTEGER {
    Other (1),                  -- Other reason instead of reason below
    InvalidCfg (2),             -- Validation failure
    PhysicalFailure (3),        -- Physical layer failure on the target cell
    Rach (4),                   -- T304 expiry due to RACH failure on target cell
    RachMeasConfigIncluded (5),  -- T304 expiry due to RACH failure on target cell when MeasConfig IE was included
    NasFailure (6)              -- NAS Failure
}

        -------------------------------------------------------------------------------
        ------      mdmiWifi IP Messages                                   ------------
        -------------------------------------------------------------------------------

-- IP Packets, header defined by RFC 791 and RFC 2460
-- Note: IPv6 jumbograms (size > 65536) not supported
-- Default IP Header logging: includes entire IP header only, regardless of embedded stream type (egs UDP/TCP/RTP/SIP)
wifi-ip-OTA-Packet OBJECT-TYPE
    SYNTAX  IpPacketReport
    ACCESS  read-only
    STATUS  mandatory
    DESCRIPTION
    "IP OTA Packet"
::= {wifiIpMessages 1}

-- SIP Messages from RFC 3261
-- SIP , includes IP header , TCP/UDP header, SIP payload plus options
wifi-sip-OTA-Message OBJECT-TYPE
    SYNTAX  SipMessageReport
    ACCESS  read-only
    STATUS  mandatory
    DESCRIPTION
    "SIP OTA Message"
::= {wifiIpMessages 2}

-- RTP Messages from RFC 3550
-- RTP (only header), includes IP header/TCP/UDP header and the RTP header
wifi-rtp-OTA-Message OBJECT-TYPE
    SYNTAX  RtpMessageReport
    ACCESS  read-only
    STATUS  mandatory
    DESCRIPTION
    "RTP OTA Message"
::= {wifiIpMessages 3}

-- IP Packets, header defined by RFC 791 and RFC 2460
-- Note: IPv6 jumbograms (size > 65536) not supported
-- Entire IP header plus payload, only for engg builds
wifiIpOtaPacketWithPayload OBJECT-TYPE
    SYNTAX  IpPacketReport
    ACCESS  read-only
    STATUS  mandatory
    DESCRIPTION
    "IP OTA Packet"
::= {wifiIpMessages 4}

-- includes IP header , TCP/UDP header, unencrypted ISAKMP payload
wifi-ISAKMP-OTA-Message OBJECT-TYPE
    SYNTAX  IsakmpMessageReport
    ACCESS  read-only
    STATUS  mandatory
    DESCRIPTION
    "ISAKMP Message"
::= {wifiIpMessages 5}

    IsakmpMessageReport ::= SEQUENCE {
        ip-version      IpVersion,
        direction       OtaMessageDirection,
        isakmpPayload   OCTET STRING(SIZE (1..65536)) 
    }

-- includes IP header , TCP/UDP header, DNS message payload
wifi-DNS-OTA-Message OBJECT-TYPE
    SYNTAX  DnsMessageReport
    ACCESS  read-only
    STATUS  mandatory
    DESCRIPTION
    "DNS Message"
::= {wifiIpMessages 7}


-------------------------------------------------------------------------------
------      mdmiIms                                                ------------
-------------------------------------------------------------------------------
imsDebug    OBJECT IDENTIFIER ::= { mdmiIms 1 }
imsSip      OBJECT IDENTIFIER ::= { mdmiIms 2 }
imsRtp      OBJECT IDENTIFIER ::= { mdmiIms 3 }

imsSipDebug             OBJECT IDENTIFIER ::= { imsSip 1 }
imsSipKpis              OBJECT IDENTIFIER ::= { imsSip 2 }
imsSipEvents            OBJECT IDENTIFIER ::= { imsSip 3 }

imsRtpDebug             OBJECT IDENTIFIER ::= { imsRtp 1 }
imsRtpKpis              OBJECT IDENTIFIER ::= { imsRtp 2 }
imsRtpEvents            OBJECT IDENTIFIER ::= { imsRtp 3 }

    -------------------------------------------------------------------------------
    ------      mdmiIms SIP                                            ------------
    -------------------------------------------------------------------------------
        -------------------------------------------------------------------------------
        ------      mdmiIms SIP KPIs                                       ------------
        -------------------------------------------------------------------------------
        -------------------------------------------------------------------------------
        ------      mdmiIms SIP Events                                     ------------
        -------------------------------------------------------------------------------

-- This log is generated whenever the call is connected or disconnected
volteCallEvent OBJECT-TYPE
    SYNTAX  VolteCallEvent
    ACCESS  read-only
    STATUS  mandatory
    DESCRIPTION
    "VoLTE cal event"
::= {imsSipEvents 1}

    VolteCallEvent ::= SEQUENCE {
        callStatus      CallStatus,
        callType        CallType
    }

-- This log is generated whenever there is a SIP registration attempt
sipRegistrationEvent OBJECT-TYPE
    SYNTAX  SipRegistrationEvent
    ACCESS  read-only
    STATUS  mandatory
    DESCRIPTION
    "SIP registration failure event"
::= {imsSipEvents 2}

    SipRegistrationEvent ::= SEQUENCE {
        registrationType    RegistrationType,
        registrationResult  RegistrationResult
    }

    RegistrationType ::= INTEGER {
        normal (1),
        emergency (2)
    }

    RegistrationResult ::= INTEGER {
        success (0),    -- when 200 OK is received
        failure (1)     -- when any error other than 401 is received; else when 408 timeout occurs
    }

-- This log is generated whenever there is a SIP subscription attempt
sipPublishEvent OBJECT-TYPE
    SYNTAX  SipPublishEvent
    ACCESS  read-only
    STATUS  mandatory
    DESCRIPTION
    "SIP publish event"
::= {imsSipEvents 3}

    SipPublishEvent ::= CHOICE {
        publishNotAvailable   NULL,              -- publish message not available
        publishAvailable        PublishResult
    }

    PublishResult ::= INTEGER {
        success (0),    -- when 200 OK is received
        failure (1)     -- when any error other than 401 is received; else when 408 timeout occurs
    }

-- This log is generated whenever there is a SIP registration attempt
sipSubscriptionEvent OBJECT-TYPE
    SYNTAX  SipSubscriptionEvent
    ACCESS  read-only
    STATUS  mandatory
    DESCRIPTION
    "SIP subscription event"
::= {imsSipEvents 4}

    SipSubscriptionEvent ::= CHOICE {
        subscriptionNotAvalable    NULL,         -- event subscription message not available
        subscriptionAvailable      SubscriptionAvailable
    }

    SubscriptionAvailable ::= SEQUENCE {
        eventTypes              EventTypes,
        subscriptionResult      SubscriptionResult
    }

    EventTypes ::= SEQUENCE OF EventType
    EventType ::= OCTET STRING  -- this is in the header of the SUBSCRIBE, including reg, presence, conference, dialog, call-info, etc.

    SubscriptionResult ::= INTEGER {
        success (0),    -- when 200 OK received is followed by NOTIFY, and applies to all Event Types
        failure (1)     -- when any error other than 401 is received; else when 408 timeout occurs
    }

-- This log is generated whenever there is a transmission or reception of SIP INVITE and SIP BYE for MO/MT call
volteCallStateChangeEvent OBJECT-TYPE
    SYNTAX  VolteCallStateChangeEvent
    ACCESS  read-only
    STATUS  mandatory
    DESCRIPTION
    "VoLTE Call State Change event"
::= {imsSipEvents 5}
    
    VolteCallStateChangeEvent ::= SEQUENCE {
        state   CallStatus,
        cause   VolteCallStateChangeCause      -- only for from ongoing(active) to inactive, others use "notAvailable"
    }

    VolteCallStateChangeCause ::= INTEGER {
        notAvailable (0),
        normalCallClearing (1),
        callDrop(2)
    }

    -------------------------------------------------------------------------------
    ------      mdmiIms RTP                                            ------------
    -------------------------------------------------------------------------------
        -------------------------------------------------------------------------------
        ------      mdmiIms RTP KPIs                                       ------------
        -------------------------------------------------------------------------------

-- This log is generated every time the codec is successfully initialized
rtpCodec OBJECT-TYPE
    SYNTAX  RtpCodecValue
    ACCESS  read-only
    STATUS  mandatory
    DESCRIPTION
    "RTP Codec"
::= {imsRtpKpis 1}

    RtpCodecValue ::= SEQUENCE {
        ssrc        INTEGER(1..4294967295),  -- id of rtp stream
        codec       RtpCodecType,            -- Codec
        codecRate   INTEGER(1..11)           -- Codec rate
    }

    RtpCodecType ::= INTEGER {
        AMR (1),
        AMR-WB (2)
    }

-- AMC rates
--      kbps-4-75(1),   4.75 kbps
--      kbps-5-15(2),   5.15 kbps
--      kbps-5-9(3),    5.9 kbps
--      kbps-6-9(5),    6.7 kbps
--      kbps-7-4(6),    7.4 kbps
--      kbps-7-95(7),   7.95 kbps
--      kbps-10-2(8),   10.2 kbps
--      kbps-12-2(9),   12.2 kbps
--      silence(10)     Silence frame
-- AMC-WB rates
--      kbps-6-6(1),    6.6 kbps
--      kbps-8-855(2),  8.855 kbps
--      kbps-12-65(3),  12.65 kbps
--      kbps-14-25(5),  14.25 kbps
--      kbps-15-85(6),  15.85 kbps
--      kbps-18-25(7),  18.25 kbps
--      kbps-19-85(8),  19.85 kbps
--      kbps-23-05(9),  23.05 kbps
--      kbps-23-85(10), 23.85 kbps
--      silence(11)     Silence frame

-- This log is generated at the receiving end of RTP flow when newReceivedSequenceNumber - lastReceivedSequenceNumber > 1
rtpPacketLoss OBJECT-TYPE
    SYNTAX  RtpPacketLossValue
    ACCESS  read-only
    STATUS  mandatory
    DESCRIPTION
    "RTP Packets Lost"
::= {imsRtpKpis 2}

    RtpPacketLossValue ::= SEQUENCE {
        ssrc        INTEGER(1..4294967295),          -- id of RTP stream
        packetsLost INTEGER(1..65535)                -- number of RTP packets lost
    }

rtpOneWayDelay OBJECT-TYPE
    SYNTAX  RtpOneWayDelayValue
    ACCESS  read-only
    STATUS  mandatory
    DESCRIPTION
    "RTP One Way Delay"
::= {imsRtpKpis 3}

    RtpOneWayDelayValue ::= SEQUENCE {
        ssrc       INTEGER(1..4294967295),   -- id of RTP stream
        delay      INTEGER(1..65535)         -- one way delay in ms
    }

rtpJitter OBJECT-TYPE
    SYNTAX  RtpJitterValue
    ACCESS  read-only
    STATUS  mandatory
    DESCRIPTION
    "RTP Jitter"
::= {imsRtpKpis 4}

    RtpJitterValue ::= SEQUENCE {
        ssrc       INTEGER(1..4294967295),   -- id of RTP stream
        jitter     INTEGER(1..65535)         -- jitter in ms
    }

-- This log is generated every 20ms, and the sequence number is the one at that 20ms instant 
rtpJitterBufferDelay OBJECT-TYPE
    SYNTAX  RtpJitterBufferDelayValue
    ACCESS  read-only
    STATUS  mandatory
    DESCRIPTION
    "RTP Jitter Buffer Delay"
::= {imsRtpKpis 5}

    RtpJitterBufferDelayValue ::= SEQUENCE {
        ssrc                INTEGER(1..4294967295),         -- id of RTP stream
        rtpSequenceNumber   INTEGER(0..65536),              -- the sequence number at the 20ms instant 
        jitterBufferDelay   INTEGER(1..65535)               -- jitter buffer delay in ms
    }

        -------------------------------------------------------------------------------
        ------      mdmiIms RTP Events                                     ------------
        -------------------------------------------------------------------------------  

-------------------------------------------------------------------------------
------      mdmiCommands                                           ------------
-------------------------------------------------------------------------------
-- Make a call
make-call OBJECT-TYPE
    SYNTAX  PhoneNumber
    ACCESS  write-only
    STATUS  mandatory
    DESCRIPTION
    "Set this field to make a call."
::= {mdmiCommands 1}

    --Digits of phone number to call
    PhoneNumber ::= SEQUENCE (SIZE (1..15)) OF INTEGER (0..9)


-------------------------------------------------------------------------------
------      mdmiLteMiddleware                                              ------------
-------------------------------------------------------------------------------
lteMWDebug      OBJECT IDENTIFIER ::= { mdmiLteMiddleware 1 }
lteMWeMBMS      OBJECT IDENTIFIER ::= { mdmiLteMiddleware 2 }

lteMWeMBMSDebug         OBJECT IDENTIFIER ::= { lteMWeMBMS 1 }
lteMWeMBMSKpis          OBJECT IDENTIFIER ::= { lteMWeMBMS 2 }
lteMWeMBMSEvents        OBJECT IDENTIFIER ::= { lteMWeMBMS 3 }
lteMWeMBMSFile          OBJECT IDENTIFIER ::= { lteMWeMBMS 4 }

-- This log is generated at the start of SDCH reception
embmsSdchReceptionEvent OBJECT-TYPE
    SYNTAX  SDCHReceptionEvent
    ACCESS  read-only
    STATUS  mandatory
    DESCRIPTION
    "SDCH Reception Event"
::= {lteMWeMBMSEvents 1}

    SDCHReceptionEvent ::= SEQUENCE {
        actualTime      TimeStamp       -- Actual time of starting to receive SDCH
    }

-- This log is generated at the start of eMBMS session
embmsSessionStartEvent OBJECT-TYPE
    SYNTAX  SessionStartEvent
    ACCESS  read-only
    STATUS  mandatory
    DESCRIPTION
    "Session Start Event"
::= {lteMWeMBMSEvents 2}

    SessionStartEvent ::= SEQUENCE {
        actualTime      TimeStamp,       -- Actual session start time per TMGI 
        tmgi            TMGI             -- Active TMGI value
    }

-- This log is generated at the end of eMBMS session
embmsSessionStopEvent OBJECT-TYPE
    SYNTAX  SessionStopEvent
    ACCESS  read-only
    STATUS  mandatory
    DESCRIPTION
    "Session Stop Event"
::= {lteMWeMBMSEvents 3}

    SessionStopEvent ::= SEQUENCE {
        actualTime      TimeStamp,      -- Actual session stop time per TMGI 
        tmgi            TMGI            -- Active TMGI value
    }

-- This log is generated when rejoin service timer expires
embmsRejoinServiceTimerExpiredEvent OBJECT-TYPE
    SYNTAX  RejoinServiceTimerExpiredEvent
    ACCESS  read-only
    STATUS  mandatory
    DESCRIPTION
    "Rejoin Service Timer Expired Event"
::= {lteMWeMBMSEvents 4}

    RejoinServiceTimerExpiredEvent ::= SEQUENCE {
        actualTime      TimeStamp       -- Actual time of rejoin service timer expires
    }

-- This log is generated when UE moves out of MBSFM service area
embmsOutServiceAreaEvent OBJECT-TYPE
    SYNTAX  OutServiceAreaEvent
    ACCESS  read-only
    STATUS  mandatory
    DESCRIPTION
    "Out Service Area Event"
::= {lteMWeMBMSEvents 5}

    OutServiceAreaEvent ::= SEQUENCE {
        actualTime      TimeStamp       -- Actual time when moving out of MBSFM service area before Hysterises
    }

-- This log is generated when UE moves into MBSFM service area
embmsInServiceAreaEvent OBJECT-TYPE
    SYNTAX  InServiceAreaEvent
    ACCESS  read-only
    STATUS  mandatory
    DESCRIPTION
    "In Service Area Event"
::= {lteMWeMBMSEvents 6}

    InServiceAreaEvent ::= SEQUENCE {
        actualTime      TimeStamp       -- Actual time when moving in to MBSFN service area after Hysterises
    }

-- This log is generated when a segment which was in the past an no longer available is requested and arrives to the DASH Client
embmsLateSegmentArrivalEvent OBJECT-TYPE
    SYNTAX  LateSegmentArraivalEvent
    ACCESS  read-only
    STATUS  mandatory
    DESCRIPTION
    "Late Segment Arraival Event"
::= {lteMWeMBMSEvents 7}

    LateSegmentArraivalEvent ::= SEQUENCE {
        lateSegmentArrivalTime      INTEGER,      -- Late segment arrival time in millisecond per TMGI
        tmgi                        TMGI          -- Active TMGI value
    }

-- This log is generated when a DASH HTTP error happens
embmsDashHttpErrorEvent OBJECT-TYPE
    SYNTAX  DashHttpErrorEvent
    ACCESS  read-only
    STATUS  mandatory
    DESCRIPTION
    "DASH HTTP Error Event"
::= {lteMWeMBMSEvents 8}

    DashHttpErrorEvent ::= SEQUENCE {
        httpErrorCode      INTEGER,       -- HTTP error code (4xx) per TMGI
        tmgi               TMGI           -- Active TMGI value
    }

-- This log is generated when a file download succeeded or failed
embmsFileDownloadCompleteEvent OBJECT-TYPE
    SYNTAX  FileDownloadCompleteEvent
    ACCESS  read-only
    STATUS  mandatory
    DESCRIPTION
    "File Download Complete Event"
::= {lteMWeMBMSEvents 9}

    FileDownloadCompleteEvent ::= SEQUENCE {
        fileName      OCTET STRING,         -- full name with path
        success       BOOLEAN,              -- success for failure
        tmgi          TMGI                  -- Active TMGI value
    }

-- This log is generated when DASH Client requests a segment which is in the past and no longer available
embmsDashClientLateRequestEvent OBJECT-TYPE
    SYNTAX  DashClientLateRequestEvent
    ACCESS  read-only
    STATUS  mandatory
    DESCRIPTION
    "Dash Client Late Request Event"
::= {lteMWeMBMSEvents 10}

    DashClientLateRequestEvent ::= SEQUENCE {
        timeDifference   INTEGER,     -- The time difference between the request time and the last time the requested segment was available. In millisecond per TMGI
        tmgi             TMGI         -- Active TMGI value
    }

-- This log is generated when initialization time bootconfig data updated or multicast received any change in bootconfig file.
embmsBootconfigFileEvent OBJECT-TYPE
    SYNTAX  BootConfigFileEvent
    ACCESS  read-only
    STATUS  mandatory
    DESCRIPTION
    "Boot config file event"
::= {lteMWeMBMSEvents 11}

BootConfigFileEvent ::= SEQUENCE {
    bootConfigFileContent               OCTET STRING        -- This KPI should be included at the top of every logging file
}

-- This log is generated when every rejoin happens
embmsSAFileEvent OBJECT-TYPE
    SYNTAX  SAFileEvent
    ACCESS  read-only
    STATUS  mandatory
    DESCRIPTION
    "SA file event"
::= {lteMWeMBMSEvents 12}

SAFileEvent ::= SEQUENCE {
    saFile          OCTET STRING            -- Include the SA content
}

-- This log is generated when the application is registered or deregistered during service initialization
embmsRegisteredAppListEvent OBJECT-TYPE
    SYNTAX  RegisteredAppListEvent
    ACCESS  read-only
    STATUS  mandatory
    DESCRIPTION
    "Registered App List Event"
::= {lteMWeMBMSEvents 13}

RegisteredAppListEvent ::= SEQUENCE {
    registeredAppList   SEQUENCE OF AppInstanceID
}

AppInstanceID ::= OCTET STRING

-- This log is generated when the logging starts and the value is updated
embmsServiceAnnouncementEvent OBJECT-TYPE
    SYNTAX  ServiceAnnouncementEvent
    ACCESS  read-only
    STATUS  mandatory
    DESCRIPTION
    "ServiceAnnouncement"
::= {lteMWeMBMSEvents 14}

    ServiceAnnouncementEvent ::= SEQUENCE OF ServiceAnnouncementSession     -- Include all of the services (not only for updated ones) in service announcement, including rejoin scenario.
    ServiceAnnouncementSession ::= SEQUENCE {
        serviceID           OCTET STRING,                   -- Service ID as in service announcement
        frequencyList       SEQUENCE OF Earfcn,             -- The list of frequencies (EARFCN) on which the TMGI to be activated is available
        tmgiList            SEQUENCE OF TMGI,               -- The list of Active TMGI's for each MBSFN area
        saiList             SEQUENCE OF INTEGER,            -- The list of SAI where the requested TMGI is present
        serviceClassList    SEQUENCE OF ServiceClass        -- The list of service class
    }

    TMGI ::= OCTET STRING
    ServiceClass ::= OCTET STRING

-- This log is generated when the application is registered or deregistered during service initialization
embmsAppRegisteredEvent OBJECT-TYPE
    SYNTAX  AppRegisteredEvent
    ACCESS  read-only
    STATUS  mandatory
    DESCRIPTION
    "Registered App Event"
::= {lteMWeMBMSEvents 15}

AppRegisteredEvent ::= SEQUENCE {
    appRegisteredEvent   SEQUENCE OF AppInstanceID          -- List of registered Applications IDs, should be updated after app deregister or re-register during service announcement
}

-- This log is generated when update received from network for File repair
embmsOffsetTimeFREvent OBJECT-TYPE
    SYNTAX  OffsetTimeFREvent
    ACCESS  read-only
    STATUS  mandatory
    DESCRIPTION
    "Offset time for file repair event"
::= {lteMWeMBMSEvents 16}

OffsetTimeFREvent ::= SEQUENCE {
    offsetTimeForFileRepair             INTEGER,             -- The back off window set by network in second per TMGI
    tmgi                                TMGI                 -- Active TMGI value
}

-- This log is generated when File repair is initiated from MMW
embmsRandomTimePeriodFREvent OBJECT-TYPE
    SYNTAX  RandomTimePeriodFREvent
    ACCESS  read-only
    STATUS  mandatory
    DESCRIPTION
    "Random time period for file repair event"
::= {lteMWeMBMSEvents 17}

RandomTimePeriodFREvent ::= SEQUENCE {
    randomTimePeriodForFileRepair       INTEGER,            -- The random period selected by MMW in second per TMGI
    tmgi                                TMGI                -- Active TMGI value
}

-- This log is generated when update received from network for Reception report
embmsOffsetTimeRREvent OBJECT-TYPE
    SYNTAX  OffsetTimeRREvent
    ACCESS  read-only
    STATUS  mandatory
    DESCRIPTION
    "Offset time for reception report event"
::= {lteMWeMBMSEvents 18}

OffsetTimeRREvent ::= SEQUENCE {
    offsetTimeforReceptionReport        INTEGER,            -- The back off window set by network in second per TMGI
    tmgi                                TMGI                -- Active TMGI value
}

-- This log is generated when Reception report is initiated from MMW
embmsRandomTimePeriodRREvent OBJECT-TYPE
    SYNTAX  RandomTimePeriodRREvent
    ACCESS  read-only
    STATUS  mandatory
    DESCRIPTION
    "Random time period reception report event"
::= {lteMWeMBMSEvents 19}

RandomTimePeriodRREvent ::= SEQUENCE {
    randomTimePeriodForReceptionReport  INTEGER,            -- The random period selected by MMW in second per TMGI
    tmgi                                TMGI                -- Active TMGI value
}

-- This log is generated when a channel is selected
embmsChannelChangeTimeEvent OBJECT-TYPE
    SYNTAX  ChannelChangeTimeEvent
    ACCESS  read-only
    STATUS  mandatory
    DESCRIPTION
    "Channel change time event"
::= {lteMWeMBMSEvents 20}

ChannelChangeTimeEvent ::= SEQUENCE {
    channelChangeTime                   INTEGER,            -- The time between a command to select a channel to the time of the new video frame displayed. In millisecond per TMGI
    tmgi                                TMGI                -- Active TMGI value
}

-- This log is generated every 1s
embmsServiceQuality OBJECT-TYPE
    SYNTAX  ServiceQuality
    ACCESS  read-only
    STATUS  mandatory
    DESCRIPTION
    "Service Quality"
::= {lteMWeMBMSFile 2}

    ServiceQuality ::= SEQUENCE {
        totalSegments                       INTEGER,            -- Total received segments during each service session per TMGI
        streamFECFailureRate                INTEGER(0..100),    -- After FEC failure rate for streaming as percentage value less than 100 per TMGI, other parameters value will be -1 except TMGi
        fileFECFailureRate                  INTEGER(0..100),    -- After FEC failure rate for file downloading as percentage value less than 100 per TMGI , other parameters value will be -1 except TMGI
        totalSegmentsLost                   INTEGER,            -- Total segments lost during each session per TMGI
        tmgi                                TMGI                -- Active TMGI value
    }



-------------------------------------------------------------------------------
------      mdmiWcdma                                              ------------
-------------------------------------------------------------------------------
wcdmaDebug    OBJECT IDENTIFIER ::= { mdmiWcdma 1 }
wcdmaRrc      OBJECT IDENTIFIER ::= { mdmiWcdma 2 }
wcdmaMac      OBJECT IDENTIFIER ::= { mdmiWcdma 3 }
wcdmaRlc      OBJECT IDENTIFIER ::= { mdmiWcdma 4 }
wcdmaPhy      OBJECT IDENTIFIER ::= { mdmiWcdma 5 }

wcdmaRrcDebug         OBJECT IDENTIFIER ::= { wcdmaRrc 1 }
wcdmaRrcKpis          OBJECT IDENTIFIER ::= { wcdmaRrc 2 }
wcdmaRrcEvents        OBJECT IDENTIFIER ::= { wcdmaRrc 3 }
wcdmaRrcMessages      OBJECT IDENTIFIER ::= { wcdmaRrc 4 }

wcdmaMacDebug         OBJECT IDENTIFIER ::= { wcdmaMac 1 }
wcdmaMacKpis          OBJECT IDENTIFIER ::= { wcdmaMac 2 }
wcdmaMacEvents        OBJECT IDENTIFIER ::= { wcdmaMac 3 }
wcdmaMacMessages      OBJECT IDENTIFIER ::= { wcdmaMac 4 }

wcdmaRlcDebug         OBJECT IDENTIFIER ::= { wcdmaRlc 1 }
wcdmaRlcKpis          OBJECT IDENTIFIER ::= { wcdmaRlc 2 }
wcdmaRlcEvents        OBJECT IDENTIFIER ::= { wcdmaRlc 3 }
wcdmaRlcMessages      OBJECT IDENTIFIER ::= { wcdmaRlc 4 }

wcdmaPhyDebug             OBJECT IDENTIFIER ::= { wcdmaPhy 1 }
wcdmaPhyMeasurements      OBJECT IDENTIFIER ::= { wcdmaPhy 2 }
wcdmaPhyEvents            OBJECT IDENTIFIER ::= { wcdmaPhy 3 }
wcdmaPhyPhysicalChannels  OBJECT IDENTIFIER ::= { wcdmaPhy 4 }
wcdmaPhyTransportChannels OBJECT IDENTIFIER ::= { wcdmaPhy 5 }


    -------------------------------------------------------------------------------
    ------      mdmiWcdma Common Fields                                ------------
    -------------------------------------------------------------------------------
LogicalChannelName ::= INTEGER {
        BCCH (0),
        PCCH (1),
        CCCH (2),
        DCCH (3),
        CTCH (4),
        DTCH (5)
    }

    -------------------------------------------------------------------------------
    ------      mdmiWcdma RRC                                          ------------
    -------------------------------------------------------------------------------
        -------------------------------------------------------------------------------
        ------      mdmiWcdma RRC Kpis                                     ------------
        -------------------------------------------------------------------------------
-- This log is generated every 1s
wcdmaRrcProtocolStates OBJECT-TYPE
    SYNTAX  WcdmaRrcProtocolStates
    ACCESS  read-only
    STATUS  mandatory
    DESCRIPTION
    "WCDMA RRC protocol states"
::= {wcdmaRrcKpis 1}

    WcdmaRrcProtocolStates ::= RrcState

-- This log is generated every 1s
wcdmaSystemInfomation OBJECT-TYPE
    SYNTAX  WcdmaSystemInformation
    ACCESS  read-only
    STATUS  mandatory
    DESCRIPTION
    "WCDMA System information"
::= {wcdmaRrcKpis 2} 

    WcdmaSystemInformation ::= SEQUENCE {
        ulUarfcn                        INTEGER,                      -- UTRA UL Absolute RF channel number
        dlUarfcn                        INTEGER,                      -- UTRA DL Absolute RF channel number
        cellId                          INTEGER,
        cellAccessRestriction           CellAccessRestriction,
        callAccess                      AllowedAccess
    }

    CellAccessRestriction ::= SEQUENCE {
        cellBarred                      BOOLEAN,
        cellReserved                    BOOLEAN,
        cellReservedForSolsa            BOOLEAN,
        ueCampedOnCell                  BOOLEAN
    }

    AllowedAccess ::= INTEGER {
        AllCalls (0),
        EmergencyCallOnly (1)
    }

        -------------------------------------------------------------------------------
        ------      mdmiWcdma RRC Events                                   ------------
        -------------------------------------------------------------------------------
wcdmaRrcErrorReport OBJECT-TYPE
    SYNTAX  WcdmaRrcErrorReport
    ACCESS  read-only
    STATUS  mandatory
    DESCRIPTION
    "WCDMA RRC Error Report"
::= {wcdmaRrcEvents 1} 

    WcdmaRrcErrorReport ::= SEQUENCE {
        rrcState                        RrcState,
        rrcProcedure                    RrcProcedure
    }

    RrcProcedure ::= INTEGER 
    -- (0) Cell selection/reselection procedure
    -- (1) SIB processing procedure
    -- (2) Paging type 2 procedure
    -- (3) Measurement control/report procedure
    -- (4) RRC connection establishment procedure
    -- (5) RRC connection release procedure
    -- (6) UE capability information
    -- (7) UE capability enquiry
    -- (8) Initial direct transfer
    -- (9) Uplink direct transfer 
    -- (10) Downlink direct transfer 
    -- (11) Signaling connection release 
    -- (12) Signaling connection release request 
    -- (13) Counter check 
    -- (14) Radio bearer establishment 
    -- (15) Radio bearer reconfiguration 
    -- (16) Radio bearer release 
    -- (17) Transport channel reconfiguration 
    -- (18) Physical channel reconfiguration 
    -- (19) Transport format combination control 
    -- (20) Cell update procedure 
    -- (21) URA update procedure 
    -- (22) UTRAN mobility information 
    -- (23) Active set update in soft handover 
    -- (24) Intersystem handover from UTRAN 
    -- (25) Intersystem handover to UTRAN 
    -- (26) Intersystem cell reselection from UTRAN 
    -- (27) Intersystem cell reselection to UTRAN 
    -- (28) Paging type 1 procedure 
    -- (29) Security mode control procedure

        -------------------------------------------------------------------------------
        ------      mdmiWcdma RRC Messages                                 ------------
        -------------------------------------------------------------------------------
wcdmaRrcSignalingMessages OBJECT-TYPE
    SYNTAX  WcdmaRrcSignalingMessages
    ACCESS  read-only
    STATUS  mandatory
    DESCRIPTION
    "WCDMA RRC Signaling Messages"
::= {wcdmaRrcMessages 1} 

    WcdmaRrcSignalingMessages ::= SEQUENCE {
        logicalChannelName                      LogicalChannelName,
        radioBearerId                           INTEGER(0..31),
        messageLength                           INTEGER,
        messageName                             OCTET STRING
    }


    -------------------------------------------------------------------------------
    ------      mdmiWcdma RLC                                          ------------
    -------------------------------------------------------------------------------
        -------------------------------------------------------------------------------
        ------      mdmiWcdma RLC Kpis                                     ------------
        -------------------------------------------------------------------------------
-- This log is generated every 50ms
wcdmaRlcAmUlStatistics OBJECT-TYPE
    SYNTAX  WcdmaRlcAmUlStatistics
    ACCESS  read-only
    STATUS  mandatory
    DESCRIPTION
    "WCDMA RLC AM Uplink statistics"
::= {wcdmaRlcKpis 1}

    WcdmaRlcAmUlStatistics ::= SEQUENCE OF WcdmaRlcAmUlEntity

    WcdmaRlcAmUlEntity ::= SEQUENCE {
        ulAmdLogicalChannelId                           INTEGER(0..255),
        ulControlLogicalChannelId                       INTEGER(0..255),
        logicalChannelName                              LogicalChannelName,
        numRlcResets                                    INTEGER,
        txPduByteCount                                  INTEGER,
        txSduByteCount                                  INTEGER,
        txPduCount                                      INTEGER,
        retxPduCount                                    INTEGER,
        numSentNak                                      INTEGER,
        txControlPduCount                               INTEGER
    }

-- This log is generated every 50ms
wcdmaRlcAmDlStatistics OBJECT-TYPE
    SYNTAX  WcdmaRlcAmDlStatistics
    ACCESS  read-only
    STATUS  mandatory
    DESCRIPTION
    "WCDMA RLC AM Downlink statistics"
::= {wcdmaRlcKpis 2}

    WcdmaRlcAmDlStatistics ::= SEQUENCE OF WcdmaRlcAmDlEntity

    WcdmaRlcAmDlEntity ::= SEQUENCE {
        dlAmdLogicalChannelId                           INTEGER(0..255),
        dlControlLogicalChannelId                       INTEGER(0..255),
        logicalChannelName                              LogicalChannelName,
        receivedPduByteCount                            INTEGER,
        receivedSduByteCount                            INTEGER,
        unrecoverablePduCount                           INTEGER,
        receivedDataPduCount                            INTEGER,
        receivedControlPduCount                         INTEGER,
        numReceivedNak                                  INTEGER
    }


-- This log is generated every 50ms
wcdmaRlcAmUlConfig OBJECT-TYPE
    SYNTAX  WcdmaRlcAmUlConfig
    ACCESS  read-only
    STATUS  mandatory
    DESCRIPTION
    "WCDMA RLC AM Uplink Config"
::= {wcdmaRlcKpis 3}

    WcdmaRlcAmUlConfig ::= SEQUENCE OF WcdmaRlcAmUlConfigEntity

    WcdmaRlcAmUlConfigEntity ::= SEQUENCE {
        dataLogicalChannelId                                    INTEGER(0..18),
        controlLogicalChannelId                                 INTEGER(0..18),
        radioBearerId                                           INTEGER(0..31),
        logicalChannelName                                      LogicalChannelName,
        liSize                                                  LiSize,
        hfn                                                     INTEGER,                    -- Hyperframe number
        maxRetxResetPdu                                         INTEGER,                    -- Max number of retransmissions of RESET PDU
        sduDiscardTimerValue                                    INTEGER,
        rlcBufferDischargeMode                                  RlcBufferDischargeMode,
        maxRetxMrwCommand                                       INTEGER,                    -- MRW command maximum retransimission
        pollProhibitTimerValue                                  INTEGER
    }

    LiSize ::= INTEGER {
        Bits_7 (0),
        Bits_15 (1)
    }

    RlcBufferDischargeMode ::= INTEGER {
        TBE (0),
        MAXDAT (1),
        No_Discard (2)
    }

-- This log is generated every 50ms
wcdmaRlcAmDlConfig OBJECT-TYPE
    SYNTAX  WcdmaRlcAmDlConfig
    ACCESS  read-only
    STATUS  mandatory
    DESCRIPTION
    "WCDMA RLC AM Downlink Config"
::= {wcdmaRlcKpis 4}

    WcdmaRlcAmDlConfig ::= SEQUENCE OF WcdmaRlcAmConfigDlEntity

    WcdmaRlcAmConfigDlEntity ::= SEQUENCE {
        dataLogicalChannelId                                    INTEGER(0..18),
        controlLogicalChannelId                                 INTEGER(0..18),
        radioBearerId                                           INTEGER(0..31),
        logicalChannelName                                      LogicalChannelName,
        liSize                                                  LiSize,
        hfn                                                     INTEGER                    -- Hyperframe number        
    }


-- This log is generated every 50ms
wcdmaRlcUlState OBJECT-TYPE
    SYNTAX  WcdmaRlcUlStates
    ACCESS  read-only
    STATUS  mandatory
    DESCRIPTION
    "WCDMA RLC Uplink State"
::= {wcdmaRlcKpis 5}

    WcdmaRlcUlStates ::= SEQUENCE OF WcdmaRlcUlLogicalChannelStateInfo

    WcdmaRlcUlLogicalChannelStateInfo ::= SEQUENCE {
        channelId                               INTEGER(0..19),
        rlcState                                RlcUlState
    }

    RlcUlState ::= INTEGER {
        UL_NULL_STATE (0),
        TM_UL_DATA_TRANSFER_READY (1),
        UM_UL_DATA_TRANSFER_READY (2),
        UM_UL_WAITING_TO_SUSPEND (3),
        UM_UL_SUSPENDED (4),
        AM_UL_DATA_TRANSFER_READY (5),
        AM_UL_WAITING_TO_SUSPEND (6),
        AM_UL_SUSPENDED (7),
        AM_UL_RESET_PENDING (8),
        AM_UL_CONFIG_PENDING (9)
    }

-- This log is generated every 50ms
wcdmaRlcDlState OBJECT-TYPE
    SYNTAX  WcdmaRlcDlStates
    ACCESS  read-only
    STATUS  mandatory
    DESCRIPTION
    "WCDMA RLC Downlink State"
::= {wcdmaRlcKpis 6}

    WcdmaRlcDlStates ::= SEQUENCE OF WcdmaRlcDlLogicalChannelStateInfo

    WcdmaRlcDlLogicalChannelStateInfo ::= SEQUENCE {
        channelId                           INTEGER(1..19),
        rlcState                            RlcDlState
    }

    RlcDlState ::= INTEGER {
        DL_NULL_STATE (0),
        TM_DL_DATA_TRANSFER_READY (1),
        UM_DL_DATA_TRANSFER_READY (2),
        AM_DL_DATA_TRANSFER_READY (3),
        AM_DL_RESET_PENDING (4)
    }


-- This log is generated every 50ms
wcdmaRlcAmUlDataPdu OBJECT-TYPE
    SYNTAX  WcdmaRlcAmUlDataPdu
    ACCESS  read-only
    STATUS  mandatory
    DESCRIPTION
    "WCDMA RLC AM Uplink data pdu"
::= {wcdmaRlcKpis 7}

    WcdmaRlcAmUlDataPdu ::= SEQUENCE OF WcdmaRlcAmPduEntity

    WcdmaRlcAmPduEntity ::= SEQUENCE {
        channelId                   INTEGER,
        pduCountPerTti              INTEGER,
        pdus                        SEQUENCE OF PduHeader
    }

    PduHeader ::= OCTET STRING(SIZE (4))

-- This log is generated every 50ms
wcdmaRlcAmUlSignalingPdu OBJECT-TYPE
    SYNTAX  WcdmaRlcAmUlSignalingPdu
    ACCESS  read-only
    STATUS  mandatory
    DESCRIPTION
    "WCDMA RLC AM Uplink Signaling pdu"
::= {wcdmaRlcKpis 8}

    WcdmaRlcAmUlSignalingPdu ::= WcdmaRlcAmPduEntity

-- This log is generated every 50ms
wcdmaRlcAmDlSignalingPdu OBJECT-TYPE
    SYNTAX  WcdmaRlcAmDlSignalingPdu
    ACCESS  read-only
    STATUS  mandatory
    DESCRIPTION
    "WCDMA RLC AM Downlink Signaling pdu"
::= {wcdmaRlcKpis 9}

    WcdmaRlcAmDlSignalingPdu ::= WcdmaRlcAmPduEntity


-- This log is generated every 50ms
wcdmaRlcTmUl OBJECT-TYPE
    SYNTAX  WcdmaRlcTm
    ACCESS  read-only
    STATUS  mandatory
    DESCRIPTION
    "WCDMA RLC TM Uplink"
::= {wcdmaRlcKpis 10}

    WcdmaRlcTm ::= SEQUENCE OF WcdmaRlcTmLogicalChannelInfo

    WcdmaRlcTmLogicalChannelInfo ::= SEQUENCE {
        logicalChannelName                      LogicalChannelName,
        logicalChannelId                        INTEGER(0..18),
        segmentation                            BOOLEAN
    }

-- This log is generated every 50ms
wcdmaRlcUmUl OBJECT-TYPE
    SYNTAX  WcdmaRlcUm
    ACCESS  read-only
    STATUS  mandatory
    DESCRIPTION
    "WCDMA RLC UM Uplink"
::= {wcdmaRlcKpis 11}

    WcdmaRlcUm ::= SEQUENCE {
        logicalChannelName                      LogicalChannelName,
        logicalChannelId                        INTEGER(0..18),
        liSize                                  LiSize,
        hfn                                     INTEGER                    -- Hyperframe number                                     
    }

-- This log is generated every 50ms
wcdmaRlcTmDl OBJECT-TYPE
    SYNTAX  WcdmaRlcTm
    ACCESS  read-only
    STATUS  mandatory
    DESCRIPTION
    "WCDMA RLC TM Downlink"
::= {wcdmaRlcKpis 12}

-- This log is generated every 50ms
wcdmaRlcUmDl OBJECT-TYPE
    SYNTAX  WcdmaRlcUm
    ACCESS  read-only
    STATUS  mandatory
    DESCRIPTION
    "WCDMA RLC UM Downlink"
::= {wcdmaRlcKpis 13}


-- This log is generated every 1s
wcdmaRadioBearersThroughput OBJECT-TYPE
    SYNTAX  WcdmaRadioBearersThroughput
    ACCESS  read-only
    STATUS  mandatory
    DESCRIPTION
    "WCDMA Radio Bearers Throughput"
::= {wcdmaRlcKpis 14}

    WcdmaRadioBearersThroughput ::= SEQUENCE OF WcdmaRadioBearerThroughput

    WcdmaRadioBearerThroughput ::= SEQUENCE {
        radioBearerId                           INTEGER,
        dlThroughput                            INTEGER,                -- in units of bps
        ulThroughput                            INTEGER                 -- in units of bps
    }

        -------------------------------------------------------------------------------
        ------      mdmiWcdma RLC Events                                   ------------
        -------------------------------------------------------------------------------
        -------------------------------------------------------------------------------
        ------      mdmiWcdma RLC Messages                                 ------------
        -------------------------------------------------------------------------------


    -------------------------------------------------------------------------------
    ------      mdmiWcdma MAC                                          ------------
    -------------------------------------------------------------------------------
        -------------------------------------------------------------------------------
        ------      mdmiWcdma MAC Kpis                                     ------------
        -------------------------------------------------------------------------------
--This log is generated every 50ms
wcdmaMacUlLogicalChannels OBJECT-TYPE
    SYNTAX  WcdmaMacUlLogicalChannels
    ACCESS  read-only
    STATUS  mandatory
    DESCRIPTION
    "WCDMA MAC UL Logical Channels"
::= {wcdmaMacKpis 1}

    WcdmaMacUlLogicalChannels ::= SEQUENCE {
        ciphering                               BOOLEAN,
        cipheringKeyId                          INTEGER(0..3),
        hfn                                     INTEGER,
        channels                                SEQUENCE OF WcdmaMacUlLogicalChannelInfo
    }

    WcdmaMacUlLogicalChannelInfo ::= SEQUENCE {
        channelId                               INTEGER(1..32),
        logicalChannelName                      LogicalChannelName,
        rlcState                                RlcUlState,
        radioBearerId                           INTEGER(0..31),
        macId                                   INTEGER(1..15)
    }

--This log is generated every 500ms
wcdmaMacUlTrafficMeasurement OBJECT-TYPE
    SYNTAX  WcdmaMacUlTrafficMeasurement
    ACCESS  read-only
    STATUS  mandatory
    DESCRIPTION
    "WCDMA MAC UL Traffic Measurement"
::= {wcdmaMacKpis 2}

    WcdmaMacUlTrafficMeasurement ::= SEQUENCE {
        reportMode                          ReprotMode,
        eventId                             EventId,
        transportChannelName                TransportChannelName,
        radioBearerIds                      SEQUENCE OF INTEGER                
    }

    ReprotMode ::= INTEGER {
        PeriodicMode (0),
        EventTriggeredMode (1)
    }

    EventId ::= INTEGER {
        Event_4A (0),
        Event_4B (1)
    }

    TransportChannelName ::= INTEGER {
        RACH (0),
        DCH (1)
    }

--This log is generated every 50ms
wcdmaMacDlLogicalChannels OBJECT-TYPE
    SYNTAX  WcdmaMacDlLogicalChannels
    ACCESS  read-only
    STATUS  mandatory
    DESCRIPTION
    "WCDMA MAC DL Logical Channels"
::= {wcdmaMacKpis 3}

    WcdmaMacDlLogicalChannels ::= SEQUENCE {
        ciphering                               BOOLEAN,
        cipheringKeyId                          INTEGER(0..3),
        hfn                                     INTEGER,
        channels                                SEQUENCE OF WcdmaMacDlLogicalChannelInfo
    }

    WcdmaMacDlLogicalChannelInfo ::= SEQUENCE {
        channelId                               INTEGER(1..32),
        logicalChannelName                      LogicalChannelName,
        rlcState                                RlcDlState,
        radioBearerId                           INTEGER(0..31)
    }


--This log is generated every 50ms
wcdmaUlTransportFormatCombinations OBJECT-TYPE
    SYNTAX  WcdmaUlTransportFormatCombination
    ACCESS  read-only
    STATUS  mandatory
    DESCRIPTION
    "WCDMA Uplink transport format combinations"
::= {wcdmaMacKpis 4}

    WcdmaUlTransportFormatCombination ::= SEQUENCE {
        numTfc                                      INTEGER(0..127),
        transportChannels                           SEQUENCE OF TransportChannelInfo
    }

    TransportChannelInfo ::= SEQUENCE {
        channelId                               INTEGER,
        tti                                     TtiFormat,
        transportFormatIndicator                INTEGER(0..31)
    }

        -------------------------------------------------------------------------------
        ------      mdmiWcdma MAC Events                                   ------------
        -------------------------------------------------------------------------------
        -------------------------------------------------------------------------------
        ------      mdmiWcdma MAC Messages                                 ------------
        -------------------------------------------------------------------------------


    -------------------------------------------------------------------------------
    ------      mdmiWcdma Phy                                          ------------
    -------------------------------------------------------------------------------
        -------------------------------------------------------------------------------
        ------      mdmiWcdma Phy Events                                   ------------
        -------------------------------------------------------------------------------
wcdmaRachParameters OBJECT-TYPE
    SYNTAX  WcdmaRachParameters
    ACCESS  read-only
    STATUS  mandatory
    DESCRIPTION
    "WCDMA RACH Parameters"
::= {wcdmaPhyEvents 1}

    WcdmaRachParameters ::= SEQUENCE {
        msgLength                       INTEGER,
        numPreamble                     INTEGER,
        aichReport                      AichReport,                 -- AICH status of the last access slot sent
        preambleSignature               INTEGER,                    -- Signature for last access channel preamble
        numAccessSlot                   INTEGER,
        sfn                             INTEGER(0..4095),
        aichTiming                      INTEGER(0..1),
        rachTxPower                     INTEGER                     -- in units of dBm
    }

    AichReport ::= INTEGER {
        no_ack (0),
        message_done (1),
        negative_ack (2),
        ack (3),
        abort (4)
    }

wcdmaPrach OBJECT-TYPE
    SYNTAX  WcdmaPrach
    ACCESS  read-only
    STATUS  mandatory
    DESCRIPTION
    "WCDMA Prach"
::= {wcdmaPhyEvents 2}

    WcdmaPrach ::= SEQUENCE {
        maxTxPower                      INTEGER(-50..33),
        availableSignatureBitmask       OCTET STRING(SIZE (2)),
        availableSubchannelBitmask      OCTET STRING(SIZE (2)),
        spreadingFactor                 INTEGER,                    -- Minimum spreading used for every 10 ms RACH
        scramblingCodeIndex             INTEGER(0..15),
        uplinkPuncturingLimit           INTEGER,
        transportChannelId              INTEGER,
        preamblePowerRamp               INTEGER,
        maxTxPreamble                   INTEGER(1..64)
    }



        -------------------------------------------------------------------------------
        ------      mdmiWcdma Phy Measurements                             ------------
        -------------------------------------------------------------------------------
-- This log is generated every 1s
wcdmaCellReselection OBJECT-TYPE
    SYNTAX  WcdmaCellReselection
    ACCESS  read-only
    STATUS  mandatory
    DESCRIPTION
    "WCDMA Cell Reselection"
::= {wcdmaPhyMeasurements 1}

    WcdmaCellReselection ::= SEQUENCE {
        wcdmaCells              SEQUENCE OF WcdmaCellInfo,
        gsmCells                SEQUENCE OF GsmCellInfo
    }

    WcdmaCellInfo ::= SEQUENCE {
        channelFreq                 INTEGER(10562..10838),
        primaryScramblingCode       INTEGER(0..511),
        rscp                        INTEGER(-128..0),                   -- Received signal code power in dB
        cellRankUsingRscp           INTEGER,                            -- cellRankUsingRscp is cell reselection criterion (cell ranking) Rs or Rn for serving or neighbor cell, respectively, computed as per 3GPP TS 25.304, to determines how much better is the neighbor cell relative to the serving cell
        ecio                        INTEGER(-63..0),
        cellRankUsingEcio           INTEGER                             -- CellRankUsingEcio is cell reselection criterion (cell ranking) Rs or Rn for serving or neighbor cell, respectively, computed as per 3GPP TS 25.304, to determines how much better is the neighbor cell relative to the serving cell
    }

    GsmCellInfo ::= SEQUENCE {
        arfcn                   INTEGER(0..1023),                       -- Radio frequency channel number
        bsic                    OCTET STRING(SIZE (2)),                 -- Base station identity code. First byte - PLMN color; Second byte - BS color
        rssi                    INTEGER(-120..0),
        rank                    INTEGER
    }

-- This log is generated every 1s
wcdmaActiveCellSet OBJECT-TYPE
    SYNTAX  WcdmaActiveCellSet
    ACCESS  read-only
    STATUS  mandatory
    DESCRIPTION
    "WCDMA Active cell"
::= {wcdmaPhyMeasurements 2}

    WcdmaActiveCellSet ::= SEQUENCE {
        dlFreq                          INTEGER(0..16383),
        cells                           SEQUENCE OF WcdmaActiveCellInfo
    }

    WcdmaActiveCellInfo ::= SEQUENCE {
        primaryScramblingCodeIndex                  INTEGER(0..511),
        cellTpc                                     INTEGER(0..5),
        cpichDiversity                              CpichDiversity,
        secondaryCpich                              BOOLEAN,
        secondaryScramblingCodeIndex                INTEGER(0..15),
        channelizationCodeIndex                     INTEGER(0..255)
    }

    CpichDiversity ::= INTEGER {
        No_Diversity (0),
        STTD (1),
        TSTD (2),
        SSTD (3)
    }

-- This log is generated every 1s
wcdmaNeighborCellSet OBJECT-TYPE
    SYNTAX  WcdmaNeighborCellSet
    ACCESS  read-only
    STATUS  mandatory
    DESCRIPTION
    "WCDMA Neighbor cell"
::= {wcdmaPhyMeasurements 3}

    WcdmaNeighborCellSet ::= SEQUENCE OF InfoForEachFreq

    InfoForEachFreq ::= SEQUENCE {
        dlFreq                  INTEGER(0..16383),
        cells                   SEQUENCE OF WcdmaNeighborCellInfo
    }

    WcdmaNeighborCellInfo ::= SEQUENCE {
        primaryScramblingCode                   INTEGER(0..511),
        cpichDiversity                          CpichDiversity
    }


-- This log is generated every 500ms
wcdmaBler OBJECT-TYPE
    SYNTAX  WcdmaBler
    ACCESS  read-only
    STATUS  mandatory
    DESCRIPTION
    "WCDMA BLER"
::= {wcdmaPhyMeasurements 4}

    WcdmaBler ::= SEQUENCE {
        windowSize                      INTEGER,                                    -- Size of window for BLER calculation in units of frames
        wcdmaTransportChannelInfos      SEQUENCE OF WcdmaTransportChannelInfo
    }

    WcdmaTransportChannelInfo ::= SEQUENCE {
        channelId                   INTEGER,
        crcCount                    INTEGER,
        errorCrcCount               INTEGER
    }


-- This log is generated every 500ms
wcdmaDrxCycle OBJECT-TYPE
    SYNTAX  WcdmaDrxCycle
    ACCESS  read-only
    STATUS  mandatory
    DESCRIPTION
    "WCDMA DRX Cycle"
::= {wcdmaPhyMeasurements 5}

    WcdmaDrxCycle ::= SEQUENCE {
        numDrxCycle                 INTEGER,
        pagingIndicatorBit          INTEGER(0..1)           -- 0: Page off   1: Page on
    }

-- This log is generated every 50ms
wcdmaCrcStatus OBJECT-TYPE
    SYNTAX  WcdmaCrcStatus
    ACCESS  read-only
    STATUS  mandatory
    DESCRIPTION
    "WCDMA CRC Status"
::= {wcdmaPhyMeasurements 6}

    WcdmaCrcStatus ::= SEQUENCE OF WcdmaCrcCheckResult

    WcdmaCrcCheckResult ::= BOOLEAN                     -- Fail or Pass

        -------------------------------------------------------------------------------
        ------      mdmiWcdma Phy Physical Layers                          ------------
        -------------------------------------------------------------------------------
-- This log is generated every 1s
wcdmaActivePhysicalChannelsUl OBJECT-TYPE
    SYNTAX  WcdmaActivePhysicalChannelsUl
    ACCESS  read-only
    STATUS  mandatory
    DESCRIPTION
    "WCDMA active uplink physical channels parameters"
::= {wcdmaPhyPhysicalChannels 1}

    WcdmaActivePhysicalChannelsUl ::= SEQUENCE {
        maxUlTxPower                    INTEGER(-50..33),                           -- in units of dBm
        dpcchPowerOffset                INTEGER(-164..-6),                          -- in steps of 2 dB
        pcpLen                          INTEGER(0..15),                             -- Power control preamble length
        pca                             INTEGER(1..2),                              -- Power control algorithm. 1: PCA1 | 2: PCA2
        tpcStep                         INTEGER(1..2),                              -- TPC step size
        dpcchFbiLen                     INTEGER(0..2),                              -- Feedback information bits
        ulPuncturingLimit               INTEGER(40..100),                           -- in steps of 4
        initialTransmitPower            INTEGER,                                    -- in units of dBm
        dpcchSlotFormat                 INTEGER(0..5),
        scramblingCodeType              INTEGER(0..1),                              -- 0: Short | 1: Long
        scramblingCode                  INTEGER,
        spreadingFactor                 INTEGER
    }

-- This log is generated every 1s
wcdmaActiveCommonPhysicalChannelsDl OBJECT-TYPE
    SYNTAX  WcdmaActiveCommonPhysicalChannelsDl
    ACCESS  read-only
    STATUS  mandatory
    DESCRIPTION
    "WCDMA active downlink common physical channels parameters"
::= {wcdmaPhyPhysicalChannels 2}

    WcdmaActiveCommonPhysicalChannelsDl ::= SEQUENCE {
        numPhysicalChannel              INTEGER,
        dlPhysicalChannelName           DlPhysicalChannelName,
        sccpchSlotFormat                INTEGER,
        scramblingCodeIndex             INTEGER(0..8192),
        diversityMode                   INTEGER(0..1),                      -- 0: STTD disabled | 1: STTD enabled
        cctrchId                        INTEGER(0..5),
        sccpchOffset                    INTEGER,
        channelizationCodeIndex         INTEGER(0..255)
    }

    DlPhysicalChannelName ::= INTEGER {
        PCCPCH_Serving (0),
        PCCPCH_Neighbor (1),
        SCCPCH0 (2),
        SCCPCH1_on_FACH (3),
        PICH (4),
        AICH (5),
        DPCH (6),
        PDSCH (7)
    }

-- This log is generated every 1s
wcdmaActiveDedicatedPhysicalChannelsDl OBJECT-TYPE
    SYNTAX  WcdmaActiveDedicatedPhysicalChannelsDl
    ACCESS  read-only
    STATUS  mandatory
    DESCRIPTION
    "WCDMA active downlink dedicated physical channels parameters"
::= {wcdmaPhyPhysicalChannels 3}

    WcdmaActiveDedicatedPhysicalChannelsDl ::= SEQUENCE {
        diversityMode                   INTEGER(0..1),                      -- 0: STTD disabled | 1: STTD enabled
        cctrchId                        INTEGER(0..5),
        slotFormat                      INTEGER(0..16),
        wcdmaRadioLinks                 SEQUENCE OF WcdmaRadioLinkInfo
    }

    WcdmaRadioLinkInfo ::= SEQUENCE {
        toffset                                 INTEGER,
        primaryScramblingCodeIndex              INTEGER(0..8192),
        cpichUsed                               INTEGER(0..1),               -- 0: Secondary | 1: Primary
        secondaryScramblingCodeIndex            INTEGER,
        channelizationCodeIndex                 INTEGER(0..255),
        tpcIndex                                INTEGER,
        wcdmaDpchs                              SEQUENCE OF WcdmaDpch
    }

    WcdmaDpch ::= SEQUENCE {
        secondaryScramblingCodeIndex            INTEGER,
        secondaryCpichChannelizationCode        INTEGER
    }

        -------------------------------------------------------------------------------
        ------      mdmiWcdma Phy Transport Layers                         ------------
        -------------------------------------------------------------------------------
-- This log is generated every 1s
wcdmaActiveTransportChannelsDl OBJECT-TYPE
    SYNTAX  WcdmaActiveTransportChannelsDl
    ACCESS  read-only
    STATUS  mandatory
    DESCRIPTION
    "WCDMA active downlink transport channels parameters"
::= {wcdmaPhyTransportChannels 1}

    WcdmaActiveTransportChannelsDl ::= SEQUENCE {
        cctrchId                            INTEGER(0..5),
        numCctrch                           INTEGER,
        wcdmaDlTransportChannelInfos        SEQUENCE OF WcdmaDlTransportChannelInfo           
    }

    WcdmaDlTransportChannelInfo ::= SEQUENCE {
        dlTransportChannelId                    INTEGER(0..32),
        channelName                             WcdmaDlChannelName,
        codingRate                              WcdmaCodingRate,
        numCrc                                  CrcBitsNumber,
        ttiFormat                               TtiFormat,
        rateMatchingAttribute                   INTEGER(1..256),
        wcdmaDlTransportFormats                 SEQUENCE OF WcdmaDlTransportFormat
    }

    WcdmaDlChannelName ::= INTEGER {
        SBCH (0),
        NBCH (1),
        DCH (2),
        DSCH (3),
        PCH (4),
        FACH (5)
    }

    WcdmaCodingRate ::= INTEGER(0..3)
    -- 1/2 and convolutional (0)
    -- 1/3 and convolutional (1)
    -- 1/3 and turbo (2)
    -- No Coding (3)

    CrcBitsNumber ::= INTEGER(0..4)
    -- 0 (0)
    -- 8 (1)
    -- 12 (2)
    -- 16 (3)
    -- 24 (4)

    TtiFormat ::= INTEGER(0..3)
    -- 10 (0)
    -- 20 (1)
    -- 40 (2)
    -- 80 (3)

    WcdmaDlTransportFormat ::= SEQUENCE {
        tbBlockSize                     INTEGER,
        numTbBlockSize                  INTEGER
    }

-- This log is generated every 1s
wcdmaActiveTransportChannelsUl OBJECT-TYPE
    SYNTAX  WcdmaActiveTransportChannelsUl
    ACCESS  read-only
    STATUS  mandatory
    DESCRIPTION
    "WCDMA active uplink transport channels parameters"
::= {wcdmaPhyTransportChannels 2}

    WcdmaActiveTransportChannelsUl ::= SEQUENCE OF WcdmaUlTransportChannelInfo

    WcdmaUlTransportChannelInfo ::= SEQUENCE {
        dlTransportChannelId                    INTEGER(0..32),
        channelName                             WcdmaDlChannelName,
        codingRate                              WcdmaCodingRate,
        numCrc                                  CrcBitsNumber,
        ttiFormat                               TtiFormat,
        rateMatchingAttribute                   INTEGER(1..256),
        wcdmaUlTransportFormats                 SEQUENCE OF WcdmaUlTransportFormat
    }

    WcdmaUlTransportFormat ::= SEQUENCE {
        tfci                    INTEGER,
        galiosFieldCalculation  INTEGER(0..1)               -- 0: If computed | 1: If signaled
    }

-- This log is generated every 1s
wcdmaDlTransportChannelsConfig OBJECT-TYPE
    SYNTAX  WcdmaDlTransportChannelsConfig
    ACCESS  read-only
    STATUS  mandatory
    DESCRIPTION
    "WCDMA downlink transport channel configuration"
::= {wcdmaPhyTransportChannels 3}

    WcdmaDlTransportChannelsConfig ::= SEQUENCE {
        dlCctrchId                  INTEGER(0..5),
        wcdmaDlTransportChannels    SEQUENCE OF WcdmaDlTransportChannel
    }

    WcdmaDlTransportChannel ::= SEQUENCE {
        dlTransportChannelId            INTEGER(0..32),
        wcdmaDlTransportFormats1         SEQUENCE OF WcdmaDlTransportFormat1
    }

    WcdmaDlTransportFormat1 ::= SEQUENCE {
        eplus                   INTEGER(1..21864),                  -- e+ rate matching parameter
        eminus                  INTEGER(1..7288)                    -- e- rate matching parameter
    }


-------------------------------------------------------------------------------
------      mdmiHsupa                                              ------------
-------------------------------------------------------------------------------
hsupaDebug    OBJECT IDENTIFIER ::= { mdmiHsupa 1 }
hsupaMac      OBJECT IDENTIFIER ::= { mdmiHsupa 2 }
hsupaRlc      OBJECT IDENTIFIER ::= { mdmiHsupa 3 }
hsupaPhy      OBJECT IDENTIFIER ::= { mdmiHsupa 4 }

hsupaMacDebug         OBJECT IDENTIFIER ::= { hsupaMac 1 }
hsupaMacKpis          OBJECT IDENTIFIER ::= { hsupaMac 2 }
hsupaMacEvents        OBJECT IDENTIFIER ::= { hsupaMac 3 }
hsupaMacMessages      OBJECT IDENTIFIER ::= { hsupaMac 4 }

hsupaRlcDebug         OBJECT IDENTIFIER ::= { hsupaRlc 1 }
hsupaRlcKpis          OBJECT IDENTIFIER ::= { hsupaRlc 2 }
hsupaRlcEvents        OBJECT IDENTIFIER ::= { hsupaRlc 3 }
hsupaRlcMessages      OBJECT IDENTIFIER ::= { hsupaRlc 4 }

hsupaPhyDebug             OBJECT IDENTIFIER ::= { hsupaPhy 1 }
hsupaPhyMeasurements      OBJECT IDENTIFIER ::= { hsupaPhy 2 }
hsupaPhyEvents            OBJECT IDENTIFIER ::= { hsupaPhy 3 }
hsupaPhyKpis              OBJECT IDENTIFIER ::= { hsupaPhy 4 }

    -------------------------------------------------------------------------------
    ------      mdmiHsuCommon                                          ------------
    -------------------------------------------------------------------------------
Tti ::= INTEGER {
    TTI_2ms (0),
    TTI_10ms (1)
}


    -------------------------------------------------------------------------------
    ------      mdmiHsupa RLC                                          ------------
    -------------------------------------------------------------------------------
        -------------------------------------------------------------------------------
        ------      mdmiHsupa RLC Kpis                                     ------------
        -------------------------------------------------------------------------------
-- This log is generated every 500 ms
hsupaRlcAmUl OBJECT-TYPE
    SYNTAX  HsupaRlcAmUl
    ACCESS  read-only
    STATUS  mandatory
    DESCRIPTION
    "HSUPA Uplink RLC AM"
::= {hsupaRlcKpis 1}

    HsupaRlcAmUl ::= SEQUENCE OF HsupaRlcEntity

    HsupaRlcEntity ::= SEQUENCE {
        rlcId                       INTEGER(0..31),
        pdus                        SEQUENCE OF HsupaRlcPdu,
        liLength                    LiSize,
        rlcBufferNewData            INTEGER,
        rlcBufferRetxData           INTEGER,
        rlcBufferControlData        INTEGER,
        numSdu                      INTEGER,
        rlcMode                     RlcMode
    }

    HsupaRlcPdu ::= SEQUENCE {
        size                    INTEGER,
        header                  OCTET STRING
    }

        -------------------------------------------------------------------------------
        ------      mdmiHsupa RLC Events                                   ------------
        -------------------------------------------------------------------------------
        -------------------------------------------------------------------------------
        ------      mdmiHsupa RLC Messages                                 ------------
        -------------------------------------------------------------------------------


    -------------------------------------------------------------------------------
    ------      mdmiHsupa MAC                                          ------------
    -------------------------------------------------------------------------------
        -------------------------------------------------------------------------------
        ------      mdmiHsupa MAC Kpis                                     ------------
        -------------------------------------------------------------------------------

-- This log is generated every 200 ms
hsupaMacL1 OBJECT-TYPE
    SYNTAX  HsupaMacL1
    ACCESS  read-only
    STATUS  mandatory
    DESCRIPTION
    "HSUPA L1/MAC"
::= {hsupaMacKpis 1}

    HsupaMacL1 ::= SEQUENCE {
        samples                             SEQUENCE OF HsupaMacL1Sample,
        tti                                 Tti,
        etfciTableIndex                     INTEGER(0..1),
        harqProcessId                       INTEGER(0..7),
        cells                               SEQUENCE OF HsupaMacL1Cell,
        servingCell                         INTEGER(0..3)
    }

    HsupaMacL1Sample ::= SEQUENCE {
        si                                  SchedulingInfo,
        happyBit                            BOOLEAN,
        agchPresent                         BOOLEAN,
        absoluteGrantValue                  INTEGER(0..31),
        absoluteGrantScope                  INTEGER,                            -- 0: All | 1: per-HARQ
        primaryOrSecondaryErntiReceived     INTEGER,
        mac-d-present                       BOOLEAN,
        retxNumber                          INTEGER,
        servingGrantIndex                   INTEGER(0..37),
        lupr                                INTEGER,
        etfci                               INTEGER(0..127)                
    }

    HsupaMacL1Cell ::= SEQUENCE {
        rlsId                               INTEGER,
        primaryScramblingCode               INTEGER,
        tpcIndex                            INTEGER
    }

    SchedulingInfo ::= INTEGER {
        No_SI_present (0),
        SI_present_triggered_by_event_or_timer (1),
        SI_present_triggered_by_padding (2)
    }


-- This log is generated every 200 ms
hsupaMacL1Stat OBJECT-TYPE
    SYNTAX  HsupaMacL1Stat
    ACCESS  read-only
    STATUS  mandatory
    DESCRIPTION
    "HSUPA L1/MAC Statistics"
::= {hsupaMacKpis 2}

    HsupaMacL1Stat ::= SEQUENCE {
        startingFrameNumber                                 INTEGER,
        tti                                                 Tti,
        etfciTableIndex                                     INTEGER(0..1),
        numFrames                                           INTEGER,
        servingRgchUpCommandsCount                          INTEGER,
        servingRgchDownCommandCount                         INTEGER,
        servingRgchHoldCommandCount                         INTEGER,
        nonServingRgchDownCommandCount                      INTEGER,
        nonServingRgchHoldCommandCount                      INTEGER,
        numReceivedAgch                                     INTEGER,
        numNewTx                                            INTEGER,
        numRetx                                             INTEGER,
        dtxCount                                            INTEGER,
        numReceivedNackAfterMaxRetx                         INTEGER,
        mac-e-resetCount                                    INTEGER,
        numSuccessFirstRetx                                 INTEGER,
        maxPowerAllowed                                     INTEGER,
        numSentSi                                           INTEGER,
        numHappyTti                                         INTEGER
    }


-- This log is generated every 1s
hsupaMac-e-es-Config OBJECT-TYPE
    SYNTAX  HsupaMac-e-es-Config
    ACCESS  read-only
    STATUS  mandatory
    DESCRIPTION
    "HSUPA MAC-e/es configuration"
::= {hsupaMacKpis 3}

    HsupaMac-e-es-Config ::= SEQUENCE {
        tti                             Tti,
        macFlows                        SEQUENCE OF HsupaMacFlow
    }

    HsupaMacFlow ::= SEQUENCE {
        flowId                          INTEGER(0..31),
        powerOffset                     INTEGER(0..7),
        numMaxRetx                      INTEGER,
        grantType                       INTEGER(0..1),                              -- 0: Scheduled | 1: Non Scheduled
        logicalChannels                 SEQUENCE OF HsupaMacLogicalChannelInfo,
        nonScheduledGrantValue          INTEGER
    }

    HsupaMacLogicalChannelInfo ::= SEQUENCE {
        radioBearerId                   INTEGER(0..31),
        logicalChannelId                INTEGER(0..20),
        priority                        INTEGER(0..7),
        logicalChannelName              LogicalChannelName,
        rlcMode                         RlcMode
    }


-- This log is generated every 500ms
hsupaMac-i-is-Config OBJECT-TYPE
    SYNTAX  HsupaMac-i-is-Config
    ACCESS  read-only
    STATUS  mandatory
    DESCRIPTION
    "HSUPA MAC-i/is configuration"
::= {hsupaMacKpis 4}

    HsupaMac-i-is-Config ::= SEQUENCE {
        tti                             Tti,
        rrcState                        RrcState,
        samples                         SEQUENCE OF HsupaMacIisSample,
        startingFrameNumber             INTEGER,
        startingHarqId                  INTEGER
    }

    HsupaMacIisSample ::= SEQUENCE {
        txType                                      TransmissionType,
        happyBit                                    BOOLEAN,
        siType                                      SchedulingInfo,
        uePowerHeadroom                             INTEGER(0..31),
        highestPriorityLogicalChannel               INTEGER(0..13),
        highestPriorityLogicalChannelBufferStatus   INTEGER(0..13),                 
        edchBufferStatus                            INTEGER(0..13),
        segmentationType                            SegmentationType,
        sduSize                                     INTEGER(0..2048),
        logicalChannelId                            INTEGER,
        erntiType                                   INTEGER(0..1),              -- ERNTI type:  0 – Primary ERNTI (P)  1 – Secondary ERNTI (S)
        f                                           INTEGER(0..1)               -- Flag bit to indicate if any more fields are present in Mac-i header  0 – Followed by another Mac-i header  1 – Followed by Mac-is PDU
    }

    TransmissionType ::= INTEGER {
        New_Transmission (0),
        Retransmission (1),
        No_Transmission (2),
        Continue (3)
    }

    SegmentationType ::= INTEGER {
        Complete (0),
        Partial_End (1),
        Partial_Start (2),
        Partial_Middle (3)
    }

        -------------------------------------------------------------------------------
        ------      mdmiHsupa MAC Events                                   ------------
        -------------------------------------------------------------------------------
        -------------------------------------------------------------------------------
        ------      mdmiHsupa MAC Messages                                 ------------
        -------------------------------------------------------------------------------


    -------------------------------------------------------------------------------
    ------      mdmiHsupa Phy                                          ------------
    -------------------------------------------------------------------------------
        -------------------------------------------------------------------------------
        ------      mdmiHsupa Phy Events                                   ------------
        -------------------------------------------------------------------------------
        -------------------------------------------------------------------------------
        ------      mdmiHsupa Phy Measurements                             ------------
        -------------------------------------------------------------------------------
        -------------------------------------------------------------------------------
        ------      mdmiHsupa Phy Kpis                                     ------------
        -------------------------------------------------------------------------------
-- This log is generated every 500ms
hsupaDlChannelsConfig OBJECT-TYPE
    SYNTAX  HsupaDlChannelsConfig
    ACCESS  read-only
    STATUS  mandatory
    DESCRIPTION
    "HSUPA DL channels configuration"
::= {hsupaPhyKpis 1}

    HsupaDlChannelsConfig ::= SEQUENCE {
        agchUse                         AgchUse,
        agchOvsf                        INTEGER(0..255),
        agchStart                       INTEGER,                            -- Starting EUL frame number or subframe number for AGCH 
        agchEnd                         INTEGER,                            -- Ending EUL frame number or subframe number for AGCH 
        agchDpchOffset                  INTEGER,
        pErntiValid                     BOOLEAN,
        sErntiValid                     BOOLEAN,
        servingCellIndex                INTEGER,                            -- Indicates which cell is the serving cell (carrying the AGCH) Note: 0 indicates first cell is serving, 1 means second, etc
        tti                             Tti,
        servingGrantType                INTEGER,                            -- 0: Primary | 1: Secondary
        sttdOnAgch                      BOOLEAN                             -- Indicates whether STTD is used on AGCH 
    }

    AgchUse ::= INTEGER {
        NoOperation (0),
        Enable (1),
        Disable (2)
    }


-- This log is generated every 500ms
hsupaUlChannelsConfig OBJECT-TYPE
    SYNTAX  HsupaUlChannelsConfig
    ACCESS  read-only
    STATUS  mandatory
    DESCRIPTION
    "HSUPA UL channels configuration"
::= {hsupaPhyKpis 2}

    HsupaUlChannelsConfig ::= SEQUENCE {
        tti                         Tti,
        harqSoftCombiningMethod     INTEGER,                            -- 0: Increment redundancy | 1: Chase combining
        slotFormat                  INTEGER(0..3),
        maxEulSpreadingFactor       SpreadingFactor,
        maxUeSpreadingFactor        SpreadingFactor,
        edpchStart                  INTEGER,                            -- Starting EUL frame number or subframe number for E-DPCH 
        edpchEnd                    INTEGER,                            -- Ending EUL frame number or subframe number for E-DPCH     
        edpcchPowerOffset           INTEGER(0..8),
        edpdchIQ                    INTEGER,                            --  0: E-DPDCH1 mapped onto I | 1: E-DPDCH1 mapped onto Q
        servingGrant                INTEGER,
        grantType                   INTEGER,                            -- 0: Primary | 1: Secondary
        etfciThreshold2Step         INTEGER(0..37),                     -- ETFCI threshold switching from 1-step to 2-step ETFCI increments due to RGCH command; range is 0 to 3
        etfciThreshold3Step         INTEGER(0..37),                     -- ETFCI threshold switching from 2-step to 3-step ETFCI increments due to RGCH command; range is 0 to 37
        maxTxPower                  INTEGER(-50..33)                    -- in units of dBm
    }

    SpreadingFactor ::= INTEGER {
        sf4x2_and_sf2x2 (0),
        sf2x2 (1), 
        sf4x2 (2), 
        sf4 (3), 
        sf8 (4), 
        sf16 (5), 
        sf32 (6), 
        sf64 (7)
    }

-- This log is generated every 200 ms for 10ms TTI/80 ms for 2ms TTI
hsupaUlEdpcchConfig OBJECT-TYPE
    SYNTAX  HsupaUlEdpcchConfig
    ACCESS  read-only
    STATUS  mandatory
    DESCRIPTION
    "HSUPA UL E-DPCCH configuration"
::= {hsupaPhyKpis 3}

    HsupaUlEdpcchConfig ::= SEQUENCE {
        samples                         SEQUENCE OF HsupaUlEdpcchConfigSample,
        tti                             Tti,
        etfciTableIndex                 INTEGER(0..1),
        frameNumber                     INTEGER,
        firstEdpchSampleFrameNumber     INTEGER
    }

    HsupaUlEdpcchConfigSample ::= SEQUENCE {
        rsn                             INTEGER(0..3),                                  -- Retransmission sequence number
        happyBit                        BOOLEAN,
        dpchPresence                    BOOLEAN,
        numDtxSlots                     INTEGER(0..7),
        etfci                           INTEGER(0..127),
        betaEd                          INTEGER,                                        -- 0 – No power on E-DPDCH (Beta_Ed = 0) | 1 – Power on E-DPDCH (Beta_Ed > 0)
        spreadingFactor                 SpreadingFactor,
        compressedMode                  BOOLEAN,
        numPilotBitsCompressed          INTEGER(0..8),
        numPilotBitsNonCompressed       INTEGER(-3..8)
    }

-- This log is generated every 200 ms
hsupaUlEtfc OBJECT-TYPE
    SYNTAX  HsupaUlEtfc
    ACCESS  read-only
    STATUS  mandatory
    DESCRIPTION
    "HSUPA UL E-TFC"
::= {hsupaPhyKpis 4}

    HsupaUlEtfc ::= SEQUENCE {
        tti                             Tti,
        samples                         SEQUENCE OF HsupaUlEtfcSample,
        frameNumber                     INTEGER,
        firstSampleFrameNumber          INTEGER
    }

    HsupaUlEtfcSample ::= SEQUENCE {
        betaC                           INTEGER,
        betaD                           INTEGER,
        dpcchPower                      INTEGER,                                        -- in units of dBm   
        edpcchToDpcchPowerRatio         INTEGER(-5..168),
        harqPowerOffset                 INTEGER(0..6),
        retransmissionOrNot             BOOLEAN,
        highestEtfci                    INTEGER(0..128)
    }


-------------------------------------------------------------------------------
------      mdmiHsdpa                                              ------------
-------------------------------------------------------------------------------
hsdpaDebug    OBJECT IDENTIFIER ::= { mdmiHsdpa 1 }
hsdpaMac      OBJECT IDENTIFIER ::= { mdmiHsdpa 2 }
hsdpaRlc      OBJECT IDENTIFIER ::= { mdmiHsdpa 3 }
hsdpaPhy      OBJECT IDENTIFIER ::= { mdmiHsdpa 4 }

hsdpaMacDebug         OBJECT IDENTIFIER ::= { hsdpaMac 1 }
hsdpaMacKpis          OBJECT IDENTIFIER ::= { hsdpaMac 2 }
hsdpaMacEvents        OBJECT IDENTIFIER ::= { hsdpaMac 3 }
hsdpaMacMessages      OBJECT IDENTIFIER ::= { hsdpaMac 4 }

hsdpaRlcDebug         OBJECT IDENTIFIER ::= { hsdpaRlc 1 }
hsdpaRlcKpis          OBJECT IDENTIFIER ::= { hsdpaRlc 2 }
hsdpaRlcEvents        OBJECT IDENTIFIER ::= { hsdpaRlc 3 }
hsdpaRlcMessages      OBJECT IDENTIFIER ::= { hsdpaRlc 4 }

hsdpaPhyDebug             OBJECT IDENTIFIER ::= { hsdpaPhy 1 }
hsdpaPhyMeasurements      OBJECT IDENTIFIER ::= { hsdpaPhy 2 }
hsdpaPhyEvents            OBJECT IDENTIFIER ::= { hsdpaPhy 3 }
hsdpaPhyKpis              OBJECT IDENTIFIER ::= { hsdpaPhy 4 }


    -------------------------------------------------------------------------------
    ------      mdmiHsdpa RLC                                          ------------
    -------------------------------------------------------------------------------
        -------------------------------------------------------------------------------
        ------      mdmiHsdpa RLC Kpis                                     ------------
        -------------------------------------------------------------------------------
        -------------------------------------------------------------------------------
        ------      mdmiHsdpa RLC Events                                   ------------
        -------------------------------------------------------------------------------
        -------------------------------------------------------------------------------
        ------      mdmiHsdpa RLC Messages                                 ------------
        -------------------------------------------------------------------------------


    -------------------------------------------------------------------------------
    ------      mdmiHsdpa MAC                                          ------------
    -------------------------------------------------------------------------------
        -------------------------------------------------------------------------------
        ------      mdmiHsdpa MAC Kpis                                     ------------
        -------------------------------------------------------------------------------
        -------------------------------------------------------------------------------
        ------      mdmiHsdpa MAC Events                                   ------------
        -------------------------------------------------------------------------------
        -------------------------------------------------------------------------------
        ------      mdmiHsdpa MAC Messages                                 ------------
        -------------------------------------------------------------------------------


    -------------------------------------------------------------------------------
    ------      mdmiHsdpa Phy                                          ------------
    -------------------------------------------------------------------------------
        -------------------------------------------------------------------------------
        ------      mdmiHsdpa Phy Events                                   ------------
        -------------------------------------------------------------------------------
        -------------------------------------------------------------------------------
        ------      mdmiHsdpa Phy Measurements                             ------------
        -------------------------------------------------------------------------------
        -------------------------------------------------------------------------------
        ------      mdmiHsdpa Phy Kpis                                     ------------
        -------------------------------------------------------------------------------    
-- This log is generated every 1 s
hsdpaConfig OBJECT-TYPE
    SYNTAX  HsdpaConfig
    ACCESS  read-only
    STATUS  mandatory
    DESCRIPTION
    "HSDPA Configuration"
::= {hsdpaPhyKpis 1}

    HsdpaConfig ::= SEQUENCE {
        numHarqProcess                                  INTEGER,
        cqiRepetitionFactor                             INTEGER,
        ackNackRepetitionFactor                         INTEGER,
        hsdpcchOffset                                   INTEGER,                        -- HS-DPCCH Offset
        dchsdpaCarrierFreq                              INTEGER,                        -- DC-HSDPA Carrier Frequency
        cellDbIndexOfDchspaCell                         INTEGER(8..10),                 -- Cell DB index of DC-HSPA cell
        dchsdpaMeasurementPowerOffset                   INTEGER(-12..26),               -- DC-HSDPA measurement power offset
        mchsdpaCarrierFreq                              INTEGER,                        -- MC-HSDPA Carrier Frequency
        cellDbIndexOfMchspaCell                         INTEGER(8..10)                  -- Cell DB index of MC-HSPA cell
    }


-- This log is generated every 200 ms
hsdpaDecodeResults OBJECT-TYPE
    SYNTAX  HsdpaDecodeResults
    ACCESS  read-only
    STATUS  mandatory
    DESCRIPTION
    "HSDPA Decode Results"
::= {hsdpaPhyKpis 2}

    HsdpaDecodeResults ::= SEQUENCE OF HsdpaDecodeSample

    HsdpaDecodeSample ::= SEQUENCE {
        codeGroupIndicator                          INTEGER,
        codeOffsetIndicator                         INTEGER,
        modulationScheme                            INTEGER(0..1),                      -- 0: QPSK | 1: 16QAM
        harqId                                      INTEGER,
        redundancyVersion                           INTEGER,
        hsTransportBlockSize                        INTEGER
    }


-- This log is generated every 1s
hsdpaHsscchStat OBJECT-TYPE
    SYNTAX  HsdpaHsscchStat
    ACCESS  read-only
    STATUS  mandatory
    DESCRIPTION
    "HSDPA HS-SCCH Statistics"
::= {hsdpaPhyKpis 3}

    HsdpaHsscchStat ::= SEQUENCE {
        numSubframes                            INTEGER,
        numScchAttempts                         INTEGER,
        numValidScch                            INTEGER,
        numCarriers                             INTEGER
    }

-- This log is generated every 2s
hsdpaHsdschHarq OBJECT-TYPE
    SYNTAX  HsdpaHsdschHarq
    ACCESS  read-only
    STATUS  mandatory
    DESCRIPTION
    "HSDPA HS-DSCH HARQ"
::= {hsdpaPhyKpis 4}

    HsdpaHsdschHarq ::= SEQUENCE {
        numSubframes                            INTEGER,
        processes                               SEQUENCE OF HarqProcess
    }

    HarqProcess ::= SEQUENCE {
        processingId                            INTEGER,
        numNewTx                                INTEGER,
        numFaultyBlocks                         INTEGER
    }


-- This log is generated every 1s
hsdpaMacHsConfig OBJECT-TYPE
    SYNTAX  HsdpaMacHsConfig
    ACCESS  read-only
    STATUS  mandatory
    DESCRIPTION
    "HSDPA MAC HS Configuration"
::= {hsdpaPhyKpis 5}

    HsdpaMacHsConfig ::= SEQUENCE {
        mac-d-flows                             SEQUENCE OF HsdpaMacDFlow,
        macHsResetIndicator                     BOOLEAN,
        mac-ehs-enabled                         BOOLEAN,
        reorderingQueues                        ReorderingQueues
    }

    ReorderingQueues ::= SEQUENCE {              -- either of the elements is available, report null for the unavailable one
            queueIfMacEhsEnabled                CHOICE {
                queueIfMacEhsEnabled-null       NULL,                   -- not available
                queueIfMacEhsEnabled            QueueIfMacEhsEnabled
            },
            queueIfMacEhsNotEnabled             CHOICE {
                queueIfMacEhsNotEnabled-null    NULL,                   -- not available
                queueIfMacEhsNotEnabled         QueueIfMacEhsNotEnabled
            }
        }

    HsdpaMacDFlow ::= SEQUENCE {
        cctrchId                                INTEGER(0..7),                          -- CCTrCh ID
        mac-d-flowId                            INTEGER(1..8),
        numMacHsQueue                           INTEGER(1..8),
        logicalChannels                         SEQUENCE OF HsdpaMacLogicalChannel
    }

    HsdpaMacLogicalChannel ::= SEQUENCE {
        rlcLogicalChannelId                     INTEGER(0..17),
        logicalChannelName                      LogicalChannelName,
        logicalChannelMode                      LogicalChannelMode
    }

    LogicalChannelMode ::= INTEGER {
        TM (0),
        UM (1),
        AM (2)
    }

    QueueIfMacEhsEnabled ::= SEQUENCE {
        queueId                             INTEGER(0..7),
        queueWindowSize                     INTEGER
    }

    QueueIfMacEhsNotEnabled ::= SEQUENCE {
        queueId                             INTEGER(0..7),
        reorderingReleaseTimer              INTEGER,
        receiveWindowSize                   INTEGER(4..32),
        mac-d-pdus                          SEQUENCE OF MacDPdus
    }

    MacDPdus ::= SEQUENCE {
        pduSizeIndex                        INTEGER(0..7),
        pduSize                             INTEGER(1..5000)
    }

END
